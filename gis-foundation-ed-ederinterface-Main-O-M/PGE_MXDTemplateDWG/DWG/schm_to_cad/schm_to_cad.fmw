FME workspace schm_to_cad.fmw
Shutdown Python:
      import smtplib
      from email.MIMEMultipart import MIMEMultipart
      from email.MIMEBase import MIMEBase
      from email.MIMEText import MIMEText
      from email.Utils import COMMASPACE, formatdate
      from email import Encoders
      import os

      # FME variables.
      import fme
      status = fme.status
      errorMsg = fme.failureMessage
      logFile = fme.logFileName

      # E-mail message values.
      subject = "GIS to CAD Export"
      to = FME_MacroValues['EMAIL']
      sender = "GISAutoCADExportAdmi@PGE.com"
      text = "Hi," + "" + \
      "\r\n\r\n Your GIS to CAD Export completed. See attached DWG file." \
      "\r\n\r\n Thank You," \
      "\r\n\r\n EDGIS Support Team"

      # Credentials.
      AUTHREQUIRED = 0
      #smtpServer = "mail01.comp.pge.com"
      smtpServer = "mailhost.utility.pge.com"


      # Create and return a message with a logfile attachment.
      def createMessage():
      # Set up the e-mail.
       message = MIMEMultipart()
       message["Subject"] = subject
       message["To"] = to
       message["From"] = sender
       message["Date"] = formatdate(localtime=True)
       message.attach(MIMEText(text))
      # print "Mallesham"
      # Attach the logfile.
       attachment = MIMEBase("application", "octet-stream")
       #attachment.set_payload(open(FME_MacroValues['FME_SERVER_DEST_DIR'] + "\\" + FME_MacroValues['output_file_name'] + ".dwg", "rb").read())
       attachment.set_payload(open(FME_MacroValues['FME_SERVER_DEST_DIR'] + "\schm_to_cad.dwg", "rb").read())
       Encoders.encode_base64(attachment)
       attachment.add_header("Content-Disposition",
       'attachment; filename=' + FME_MacroValues['output_file_name'] + ".dwg")
       message.attach(attachment)
       return message

      # Send the passed in message.
      def sendMessage(message):
          server = smtplib.SMTP(smtpServer)
          server.sendmail(sender, to, message.as_string())
          server.quit()

      # E-mails the translation results on failure.
      def mailResults():
       message = createMessage()
       sendMessage(message)

      # Call function for FME to execute.
      mailResults()

Parameters:
- output_file_name = schm_to_cad
- _GEODBInSearchFeature_GEODATABASE_SDE = 2811770 12845610 2811770 12846767 2814716 12846767 2814716 12845610 2811770 12845610   # Search Feature
- scale = 250
- SCHM_FGDB = \\eoappgisqa01\arcgisserver\Schematic\70840135-da78-4745-bd5d-7276d429d480\SCHM.gdb   # Schematic File GDB
- SCHM_FILE_PATH = \\eoappgisqa01\arcgisserver\Schematic\20551002-436a-43f3-985c-5a2e4ad5a31a   # Schematic File Path
- SCHM_GRID = BJ\137\BJ137-K   # Schematic Grids
- SourceDataset_GEODATABASE_SDE_SCHM = $(FME_MF_DIR)edschm.sde   # Schematic SDE File
- CIRCUITIDS = :254072107:254072111:254072110:254072115:254072114:254071108:254071106:254072113:254072109:254072108:254071105
- EMAIL = disw@pge.com
- FEEDER_TYPE = -1
- VOLTAGE = -1
- FME_SERVER_DEST_DIR = c:\temp   # Fanout Directory

Readers:
- GEODATABASE_SDE_1: GEODATABASE_SDE from $(FME_MF_DIR)sde_electric.sde
- GEODATABASE_FILE_1: GEODATABASE_FILE from $(SCHM_FGDB)
- GEODATABASE_SDE_2: GEODATABASE_SDE from $(FME_MF_DIR)sde_landbase.sde

Writers:
- REALDWG_1: REALDWG to $(FME_MF_DIR)schm_to_cad.dwg in UTM83-10F

CreateSearchPolygon
    _GEODBInSearchFeature_GEODATABASE_SDE = $(_GEODBInSearchFeature_GEODATABASE_SDE)
    PythonCaller_Output -> Clipper [input 1]
    PythonCaller_Output -> ProcessWaterP_and_Seg_2 [input 3]
    PythonCaller_Output -> Clipper_3 [input 1]
    PythonCaller_Output -> Clipper_2 [input 1]
    PythonCaller_Output -> Process_CA_Street_Names [input 1]
    PythonCaller_Output -> IntersectSpatialFilter [input 1]

Bookmark: Schematic Assets
CapacitorBank (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, OPERATINGVOLTAGE integer, INSTALLATIONTYPE char(5), SYMBOLNUMBER smallint, CONVERSIONID integer, OPERATINGNUMBER char(9), DISTRICT integer, TOTALKVAR smallint, DIVISION smallint, SUBTYPECD integer,
      CIRCUITID char(9), TOTALKVR smallint, FEEDERTYPE smallint, DiagType char(48), DiagName char(48)
    -> ProcessCapacitorBank_and_Anno [input 1]
DCRectifier (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, DiagType char(48), DiagName char(48), ANCILLARYROLE smallint, ENABLED smallint, GLOBALID char(38), CREATIONUSER char(15), DATECREATED date, DATEMODIFIED date, LASTUSER char(15), CONVERSIONID integer,
      CONVERSIONWORKPACKAGE char(6), STATUS smallint, ELECTRICTRACEWEIGHT integer, CIRCUITID char(9), CIRCUITID2 char(9), CONVCIRCUITID char(9), CONVCIRCUITID2 char(9), FEEDERINFO integer, INSTALLATIONDATE date, RETIREDATE date, NUMBEROFPHASES smallint, PHASEDESIGNATION integer, PHASINGVERIFIEDSTATUS char(30), SYMBOLROTATION double, INSTALLJOBPREFIX char(3), INSTALLJOBYEAR smallint, COMMENTS char(255), CEDSADEVICEID integer, LOCALOPOFFICE char(20), SOURCESIDEDEVICEID char(20), COMPLEXDEVICEIDC char(5), CUSTOMEROWNED char(5), SYMBOLNUMBER smallint, LOCDESC char(100), COUNTY smallint, ZIP char(10), GEMSDISTMAPNUM char(10), GEMSCIRCUITMAPNUM char(10), GEMSOTHERMAPNUM char(10), ANIMALGUARDTYPE char(5),
      DIVISION smallint, DISTRICT integer, VAULT char(6), REPLACEGUID guid, SUBTYPECD integer, RECTIFIERTYPE char(20), OPERATINGVOLTAGE integer, OUTPUTVOLTAGE char(10), AMPRATING char(20), STRUCTUREGUID guid, STRUCTURECONVID integer, INSTALLATIONTYPE char(5), LOCALOFFICEID char(4), REGION char(10), INSTALLJOBNUMBER char(14), CITY char(40), OPERATINGNUMBER char(9), DCRECTIFIERSIZE char(15), RECTIFIERNUMBER char(10), TRANSFORMERGUID guid, PROTECTIVESSD char(20), AUTOPROTECTIVESSD char(20), SSDGUID char(38)
    -> ProcessDCRectifier_and_Anno
ProcessDCRectifier_and_Anno
    scale = $(scale)
    STATUS = @Value(STATUS)
    SCHEMATICTID = @Value(SCHEMATICTID)
    OPERATINGVOLTAGE = @Value(OPERATINGVOLTAGE)
    SUBTYPE = @Value(SUBTYPE)
    output_file_name = $(output_file_name)
    UGUID = @Value(UGUID)
    UOID = @Value(UOID)
    CLIENTOPERATINGVOLTAGE = $(VOLTAGE)
    CIRCUITIDS = $(CIRCUITIDS)
    CIRCUITID = @Value(CIRCUITID)
    Features -> SetDefaultPoint_3
DeviceGroup (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, DEVICEGROUPNAME char(50), STATUS smallint, CIRCUITID char(9), CONVERSIONID integer, DISTRICT integer, DIVISION smallint, DEVICEGROUPTYPE smallint, SUBTYPECD integer, FEEDERTYPE smallint, DiagType char(48),
      DiagName char(48), GLOBALID char(38), CREATIONUSER char(15), DATECREATED date, DATEMODIFIED date, LASTUSER char(15), CONVERSIONID_ integer, CONVERSIONWORKPACKAGE char(6), CUSTOMEROWNED char(5), COMMENTS char(255), STATUS_ smallint, INSTALLATIONDATE date, RETIREDATE date, INSTALLJOBPREFIX char(3), INSTALLJOBYEAR smallint, SYMBOLNUMBER smallint, GPSLATITUDE double, GPSLONGITUDE double, GPSSOURCE char(5), SOURCEACCURACY integer, MAPOFFICE char(3), DISTMAP char(20), OTHERMAP char(8), LOCDESC1 char(100), LOCDESC2 char(100), ACCESSINFO char(60), URBANRURALCODE char(1), DISTRICT_ integer, REGION char(10), DIVISION_ smallint,
      SYMBOLROTATION double, FUNCTIONALLOCATIONID char(40), COUNTY smallint, ZIP char(10), SUBTYPECD_ integer, DEVICEGROUPTYPE_ smallint, SAPEQUIPID char(18), TEMPEQUIPID char(44), STRUCTUREGUID guid, DEVICEGROUPNAME_ char(50), CIRCUITID_ char(9), LOCALOFFICEID char(4), INSTALLJOBNUMBER char(14), CITY char(40), VERSIONNAME char(64), POSITIONDESCRIPTION char(50), FEEDERTYPE_ smallint
    -> ProcessDeviceGroup_and_Anno [input 1]
EDGIS.DeviceGroupSchem500Anno (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, FEATURECONVERSIONID integer, GLOBALID char(38), FEEDERTYPE smallint, SHAPE.AREA double, SHAPE.LEN double
    -> ProcessDeviceGroup_and_Anno [input 2]
ProcessDeviceGroup_and_Anno
    SCHEMATICTID = @Value(SCHEMATICTID)
    output_file_name = $(output_file_name)
    GEODB_TEXT_STRING = @Value(geodb_text_string)
    scale = $(scale)
    FONTNAME = @Value(FONTNAME)
    FME_GEOMETRY = @Value(fme_geometry)
    ROTATION = @Value(ROTATION)
    DEVICEGROUPTYPE = @Value(DEVICEGROUPTYPE)
    STATUS = @Value(STATUS)
    ITALIC = @Value(ITALIC)
    UOID = @Value(UOID)
    CIRCUITIDS = $(CIRCUITIDS)
    FEATUREID = @Value(FEATUREID)
    OBJECTID = @Value(OBJECTID)
    FEEDERTYPE = @Value(FEEDERTYPE)
    SUBTYPE = @Value(SUBTYPE)
    BOLD = @Value(BOLD)
    UGUID = @Value(UGUID)
    CLIENTFEEDERTYPE = $(FEEDER_TYPE)
    CIRCUITID = @Value(CIRCUITID)
    Features -> SetDefaultPoint_3
    Anno -> SetOutputFileLines_2
ElectricStitchPoint (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, CIRCUITID char(9), CONVERSIONID integer, DISTRICT integer, DIVISION smallint, SUBTYPECD integer, FEEDERTYPE smallint, DiagType char(48), DiagName char(48), ANCILLARYROLE smallint,
      ENABLED smallint, GLOBALID char(38), CREATIONUSER char(15), DATECREATED date, DATEMODIFIED date, LASTUSER char(15), CONVERSIONID_ integer, CONVERSIONWORKPACKAGE char(6), SUBTYPECD_ integer, ORIGINALXCOORD double, ORIGINALYCOORD double, STITCHPOINTID char(32), CIRCUITID_ char(9), CIRCUITID2 char(9), FEEDERINFO integer, ELECTRICTRACEWEIGHT integer, PHASEDESIGNATION integer, ZIP char(10), COUNTY smallint, NORMALPOSITION integer, NORMALPOSITIONA integer, NORMALPOSITIONB integer, NORMALPOSITIONC integer, SYMBOLROTATION double, STATUS_ smallint, DISTRIBUTIONPLANNINGAREA char(30), REPLACEGUID guid, DIVISION_ smallint, LOCDESC char(255), LOCALOFFICEID char(4),
      REGION char(10), DISTRICT_ integer, CITY char(40), NOMINALVOLTAGE integer, VERSIONNAME char(64), FEEDERTYPE_ smallint
    -> ProcessElectricStitchPoint_and_Label [input 1]
EDGIS.ElecStitchPointSchem500Anno (reader GEODATABASE_SDE_1) [off]
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, FEATURECONVERSIONID integer, GLOBALID char(38), SHAPE.AREA double, SHAPE.LEN double
    -> ProcessElectricStitchPoint_and_Label [input 2]
ProcessElectricStitchPoint_and_Label
    SCHEMATICTID = @Value(SCHEMATICTID)
    output_file_name = $(output_file_name)
    GEODB_TEXT_STRING = @Value(geodb_text_string)
    ANNOTATIONCLASSID = @Value(ANNOTATIONCLASSID)
    TEXTSTRING = @Value(TEXTSTRING)
    scale = $(scale)
    FONTNAME = @Value(FONTNAME)
    FME_GEOMETRY = @Value(fme_geometry)
    ROTATION = @Value(ROTATION)
    STATUS = @Value(STATUS)
    ITALIC = @Value(ITALIC)
    UOID = @Value(UOID)
    CIRCUITIDS = $(CIRCUITIDS)
    SUBTYPECD = @Value(SUBTYPECD)
    FEATUREID = @Value(FEATUREID)
    OBJECTID = @Value(OBJECTID)
    FEEDERTYPE = @Value(FEEDERTYPE)
    SUBTYPE = @Value(SUBTYPE)
    BOLD = @Value(BOLD)
    UGUID = @Value(UGUID)
    CLIENTFEEDERTYPE = $(FEEDER_TYPE)
    CIRCUITID = @Value(CIRCUITID)
    Features -> SetDefaultPoint_3
    Labels -> SetOutputFileLines_2
    Anno -> SetOutputFileLines_2
PrimaryGeneration (reader GEODATABASE_FILE_1) [off]
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, CIRCUITID char(9), NAMEOFCOGENERATOR char(50), CONVERSIONID integer, OPERATINGNUMBER char(9), DISTRICT integer, DIVISION smallint, SUBTYPECD integer, FEEDERTYPE smallint, DiagType char(48),
      DiagName char(48), ANCILLARYROLE smallint, ENABLED smallint, GLOBALID char(38), CREATIONUSER char(15), DATECREATED date, DATEMODIFIED date, LASTUSER char(15), CONVERSIONID_ integer, CONVERSIONWORKPACKAGE char(6), STATUS_ smallint, ELECTRICTRACEWEIGHT integer, PHASEDESIGNATION integer, PHASINGVERIFIEDSTATUS char(30), CIRCUITID_ char(9), CIRCUITID2 char(9), CONVCIRCUITID char(9), CONVCIRCUITID2 char(9), FEEDERINFO integer, INSTALLATIONDATE date, LOCATIONID char(20), SYMBOLROTATION double, ELEVATION double, INSTALLJOBPREFIX char(3), INSTALLJOBYEAR smallint, LOCATIONDESC char(100), COMMENTS char(255), COUNTY smallint, ZIP char(10), REPLACEGUID guid,
      SUBTYPECD_ integer, INSTALLATIONTYPE char(5), GENERATORTYPE integer, OWNERNAME char(50), CONNECTIONCONFIGURATION char(3), KW double, POWERFACTOR double, RATEDKVA integer, GPSLATITUDE double, GPSLONGITUDE double, GPSSOURCE char(5), SOURCEACCURACY integer, SAPEQUIPID char(18), CAPACITY smallint, NAMEOFCOGENERATOR_ char(50), CEDSADEVICEID integer, CUSTOMEROWNED char(5), LOCALOFFICEID char(4), DISTRICT_ integer, DIVISION_ smallint, REGION char(10), INSTALLJOBNUMBER char(14), CITY char(40), OPERATINGNUMBER_ char(9), VERSIONNAME char(64), CAPACITYSIZE char(2), FEEDERTYPE_ smallint
    -> ProcessPrimaryGeneration_and_Anno [input 1]
EDGIS.PriGenerationSchem500Anno (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, FEATURECONVERSIONID integer, GLOBALID char(38), FEEDERTYPE smallint, SHAPE.AREA double, SHAPE.LEN double
    -> ProcessPrimaryGeneration_and_Anno [input 2]
ProcessPrimaryGeneration_and_Anno
    SCHEMATICTID = @Value(SCHEMATICTID)
    output_file_name = $(output_file_name)
    GEODB_TEXT_STRING = @Value(geodb_text_string)
    ANNOTATIONCLASSID = @Value(ANNOTATIONCLASSID)
    scale = $(scale)
    FONTNAME = @Value(FONTNAME)
    FME_GEOMETRY = @Value(fme_geometry)
    STATUS = @Value(STATUS)
    ITALIC = @Value(ITALIC)
    UOID = @Value(UOID)
    CIRCUITIDS = $(CIRCUITIDS)
    FEATUREID = @Value(FEATUREID)
    OBJECTID = @Value(OBJECTID)
    FEEDERTYPE = @Value(FEEDERTYPE)
    SUBTYPE = @Value(SUBTYPE)
    BOLD = @Value(BOLD)
    UGUID = @Value(UGUID)
    CLIENTFEEDERTYPE = $(FEEDER_TYPE)
    CIRCUITID = @Value(CIRCUITID)
    Anno -> SetOutputFileLines_2
    Features -> SetDefaultPoint_3
EDGIS.VoltageRegulatorSchem500Anno (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, FEATURECONVERSIONID integer, GLOBALID char(38), FEEDERTYPE smallint, SHAPE.AREA double, SHAPE.LEN double
    -> ProcessVoltageRegulator_and_Anno [input 2]
EDGIS.CapacitorBankSchem500Anno (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, FEATURECONVERSIONID integer, GLOBALID char(38), FEEDERTYPE smallint, SHAPE.AREA double, SHAPE.LEN double
    -> ProcessCapacitorBank_and_Anno [input 2]
ProcessCapacitorBank_and_Anno
    SCHEMATICTID = @Value(SCHEMATICTID)
    GEODB_TEXT_STRING = @Value(geodb_text_string)
    SYMBOLNUMBER_2 = @Value(SYMBOLNUMBER)
    ANNOTATIONCLASSID = @Value(ANNOTATIONCLASSID)
    scale = $(scale)
    FONTNAME = @Value(FONTNAME)
    OPERATINGVOLTAGE = @Value(OPERATINGVOLTAGE)
    FME_GEOMETRY = @Value(fme_geometry)
    STATUS = @Value(STATUS)
    ITALIC = @Value(ITALIC)
    INSTALLATIONTYPE_2 = @Value(INSTALLATIONTYPE)
    UOID = @Value(UOID)
    CIRCUITIDS = $(CIRCUITIDS)
    CLIENTOPERATINGVOLTAGE = $(VOLTAGE)
    FEATUREID = @Value(FEATUREID)
    OBJECTID = @Value(OBJECTID)
    FEEDERTYPE = @Value(FEEDERTYPE)
    SUBTYPE = @Value(SUBTYPE)
    BOLD = @Value(BOLD)
    UGUID = @Value(UGUID)
    CLIENTFEEDERTYPE = $(FEEDER_TYPE)
    CIRCUITID = @Value(CIRCUITID)
    Features -> SetDefaultPoint_3
    Anno -> SetOutputFileLines_2
DynamicProtectiveDevice (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, CIRCUITID char(9), OPERATINGVOLTAGE integer, SYMBOLNUMBER smallint, CONVERSIONID integer, OPERATINGNUMBER char(9), DISTRICT integer, DIVISION smallint, FEEDERTYPE smallint, DiagType char(48),
      DiagName char(48)
    -> ProcessDPD_and_Anno [input 2]
EDGIS.DynProtDevSchem500Anno (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, FEATURECONVERSIONID integer, GLOBALID char(38), FEEDERTYPE smallint, SHAPE.AREA double, SHAPE.LEN double
    -> ProcessDPD_and_Anno [input 1]
ProcessDPD_and_Anno
    FONTSIZE = @Value(FONTSIZE)
    SCHEMATICTID = @Value(SCHEMATICTID)
    output_file_name = $(output_file_name)
    GEODB_TEXT_STRING = @Value(geodb_text_string)
    ANNOTATIONCLASSID = @Value(ANNOTATIONCLASSID)
    TEXTSTRING = @Value(TEXTSTRING)
    scale = $(scale)
    FONTNAME = @Value(FONTNAME)
    OPERATINGVOLTAGE = @Value(OPERATINGVOLTAGE)
    SYMBOLNUMBER = @Value(SYMBOLNUMBER)
    FONTLEADING = @Value(FONTLEADING)
    FME_GEOMETRY = @Value(fme_geometry)
    ROTATION = @Value(ROTATION)
    STATUS = @Value(STATUS)
    ITALIC = @Value(ITALIC)
    UOID = @Value(UOID)
    CIRCUITIDS = $(CIRCUITIDS)
    CLIENTOPERATINGVOLTAGE = $(VOLTAGE)
    FEATUREID = @Value(FEATUREID)
    FEEDERTYPE = @Value(FEEDERTYPE)
    SUBTYPE = @Value(SUBTYPE)
    BOLD = @Value(BOLD)
    UGUID = @Value(UGUID)
    CLIENTFEEDERTYPE = $(FEEDER_TYPE)
    CIRCUITID = @Value(CIRCUITID)
    Features -> SetDefaultPoint_3
    Anno -> SetOutputFileLines_2
Fuse (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, CIRCUITID char(9), LINKRATING smallint, OPERATINGVOLTAGE integer, LINKTYPE smallint, COMPLEXDEVICEIDC char(5), CONVERSIONID integer, OPERATINGNUMBER char(9), DISTRICT integer, DIVISION smallint,
      SUBTYPECD integer, FEEDERTYPE smallint, DiagType char(48), DiagName char(48)
    -> ProcessFuse_and_Anno [input 1]
EDGIS.FuseSchem500Anno (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, FEATURECONVERSIONID integer, GLOBALID char(38), FEEDERTYPE smallint, SHAPE.AREA double, SHAPE.LEN double
    -> ProcessFuse_and_Anno [input 2]
ProcessFuse_and_Anno
    SCHEMATICTID = @Value(SCHEMATICTID)
    output_file_name = $(output_file_name)
    GEODB_TEXT_STRING = @Value(geodb_text_string)
    ANNOTATIONCLASSID = @Value(ANNOTATIONCLASSID)
    scale = $(scale)
    FONTNAME = @Value(FONTNAME)
    OPERATINGVOLTAGE = @Value(OPERATINGVOLTAGE)
    FME_GEOMETRY = @Value(fme_geometry)
    STATUS = @Value(STATUS)
    COMPLEXDEVICEIDC = @Value(COMPLEXDEVICEIDC)
    ITALIC = @Value(ITALIC)
    UOID = @Value(UOID)
    CIRCUITIDS = $(CIRCUITIDS)
    SUBTYPECD = @Value(SUBTYPECD)
    CLIENTOPERATINGVOLTAGE = $(VOLTAGE)
    FEATUREID = @Value(FEATUREID)
    OBJECTID = @Value(OBJECTID)
    FEEDERTYPE = @Value(FEEDERTYPE)
    SUBTYPE = @Value(SUBTYPE)
    BOLD = @Value(BOLD)
    UGUID = @Value(UGUID)
    CLIENTFEEDERTYPE = $(FEEDER_TYPE)
    CIRCUITID = @Value(CIRCUITID)
    Features -> SetDefaultPoint_3
    Anno -> SetOutputFileLines_2
OpenPoint (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, CIRCUITID char(9), OPERATINGVOLTAGE integer, CONVERSIONID integer, RATEDAMPS smallint, DISTRICT integer, DIVISION smallint, SUBTYPECD integer, FEEDERTYPE smallint, DiagType char(48),
      DiagName char(48)
    -> ProcessOpenPoint
ProcessOpenPoint
    scale = $(scale)
    RATEDAMPS = @Value(RATEDAMPS)
    STATUS = @Value(STATUS)
    SCHEMATICTID = @Value(SCHEMATICTID)
    OPERATINGVOLTAGE = @Value(OPERATINGVOLTAGE)
    FEEDERTYPE = @Value(FEEDERTYPE)
    SUBTYPE = @Value(SUBTYPE)
    output_file_name = $(output_file_name)
    UGUID = @Value(UGUID)
    CLIENTFEEDERTYPE = $(FEEDER_TYPE)
    UOID = @Value(UOID)
    CIRCUITIDS = $(CIRCUITIDS)
    CLIENTOPERATINGVOLTAGE = $(VOLTAGE)
    CIRCUITID = @Value(CIRCUITID)
    Features -> SetDefaultPoint_3
PrimaryMeter (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, CIRCUITID char(9), OPERATINGVOLTAGE integer, CONVERSIONID integer, OPERATINGNUMBER char(9), DISTRICT integer, DIVISION smallint, FEEDERTYPE smallint, DiagType char(48), DiagName char(48)
    -> ProcessPrimary
ProcessPrimary
    STATUS = @Value(STATUS)
    OPERATINGVOLTAGE = @Value(OPERATINGVOLTAGE)
    FEEDERTYPE = @Value(FEEDERTYPE)
    UGUID = @Value(UGUID)
    CLIENTFEEDERTYPE = $(FEEDER_TYPE)
    UOID = @Value(UOID)
    CIRCUITIDS = $(CIRCUITIDS)
    CLIENTOPERATINGVOLTAGE = $(VOLTAGE)
    CIRCUITID = @Value(CIRCUITID)
    SCHMCircuitID = 0
    -> SetPrimaryMeterBlockName
SetPrimaryMeterBlockName: AttributeCreator
    ATTR_LIST = autocad_block_name,EEPM,autocad_layer,"FME_CONDITIONAL:DEFAULT_VALUE'_FME_NO_OP_'BOOL_OP;OR;COMPOSITE_TEST;<Unused>;TEST @Value(STATUS) != 0'MAP-ELEC-EXIST-DOH'FME_NUM_CONDITIONS2___",output_file_name,$(output_file_name),autocad_entity,autocad_insert
    -> SetDefaultPoint_3
StepDown (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, CIRCUITID char(9), OPERATINGVOLTAGE integer, INSTALLATIONTYPE char(5), CONVERSIONID integer, OPERATINGNUMBER char(9), DISTRICT integer, DIVISION smallint, FEEDERTYPE smallint, DiagType char(48),
      DiagName char(48)
    -> ProcessStepDown_and_Anno [input 1]
EDGIS.StepdownSchem500Anno (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, FEATURECONVERSIONID integer, GLOBALID char(38), FEEDERTYPE smallint, SHAPE.AREA double, SHAPE.LEN double
    -> ProcessStepDown_and_Anno [input 2]
ProcessStepDown_and_Anno
    output_file_name = $(output_file_name)
    GEODB_TEXT_STRING = @Value(geodb_text_string)
    ANNOTATIONCLASSID = @Value(ANNOTATIONCLASSID)
    scale = $(scale)
    FONTNAME = @Value(FONTNAME)
    OPERATINGVOLTAGE = @Value(OPERATINGVOLTAGE)
    INSTALLATIONTYPE = @Value(INSTALLATIONTYPE)
    FME_GEOMETRY = @Value(fme_geometry)
    STATUS = @Value(STATUS)
    ITALIC = @Value(ITALIC)
    UOID = @Value(UOID)
    CIRCUITIDS = $(CIRCUITIDS)
    CLIENTOPERATINGVOLTAGE = $(VOLTAGE)
    FEATUREID = @Value(FEATUREID)
    OBJECTID = @Value(OBJECTID)
    FEEDERTYPE = @Value(FEEDERTYPE)
    SUBTYPE = @Value(SUBTYPE)
    BOLD = @Value(BOLD)
    UGUID = @Value(UGUID)
    CLIENTFEEDERTYPE = $(FEEDER_TYPE)
    CIRCUITID = @Value(CIRCUITID)
    Anno -> SetOutputFileLines_2
    Features -> SetDefaultPoint_3
Switch (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, NORMALPOSITIONB integer, NORMALPOSITIONC integer, STATUS smallint, CIRCUITID char(9), OPERATINGVOLTAGE integer, SYMBOLNUMBER smallint, CONVERSIONID integer, OPERATINGNUMBER char(9), DISTRICT integer, DIVISION smallint,
      NORMALPOSITIONA integer, FEEDERTYPE smallint, DiagType char(48), DiagName char(48)
    -> ProcessSwitches_and_Anno [input 1]
EDGIS.SwitchSchem500Anno (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, FEATURECONVERSIONID integer, GLOBALID char(38), FEEDERTYPE smallint, SHAPE.AREA double, SHAPE.LEN double
    -> ProcessSwitches_and_Anno [input 2]
ProcessSwitches_and_Anno
    SCHEMATICTID = @Value(SCHEMATICTID)
    GEODB_TEXT_STRING = @Value(geodb_text_string)
    ANNOTATIONCLASSID = @Value(ANNOTATIONCLASSID)
    SCHMCircuitID = 0
    TEXTSTRING = @Value(TEXTSTRING)
    scale = $(scale)
    FONTNAME = @Value(FONTNAME)
    OPERATINGVOLTAGE = @Value(OPERATINGVOLTAGE)
    SYMBOLNUMBER = @Value(SYMBOLNUMBER)
    FME_GEOMETRY = @Value(fme_geometry)
    STATUS = @Value(STATUS)
    ITALIC = @Value(ITALIC)
    UOID = @Value(UOID)
    CIRCUITIDS = $(CIRCUITIDS)
    CLIENTOPERATINGVOLTAGE = $(VOLTAGE)
    FEATUREID = @Value(FEATUREID)
    FEEDERTYPE = @Value(FEEDERTYPE)
    SUBTYPE = @Value(SUBTYPE)
    BOLD = @Value(BOLD)
    UGUID = @Value(UGUID)
    CLIENTFEEDERTYPE = $(FEEDER_TYPE)
    CIRCUITID = @Value(CIRCUITID)
    Features -> SetDefaultPoint_3
    Anno -> SetOutputFileLines_2
Tie (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, CIRCUITID char(9), CONVERSIONID integer, DISTRICT integer, DIVISION smallint, FEEDERTYPE smallint, DiagType char(48), DiagName char(48), ANCILLARYROLE smallint, ENABLED smallint,
      GLOBALID char(38), CREATIONUSER char(15), DATECREATED date, DATEMODIFIED date, LASTUSER char(15), CONVERSIONID_ integer, CONVERSIONWORKPACKAGE char(6), STATUS_ smallint, ELECTRICTRACEWEIGHT integer, CIRCUITID_ char(9), CIRCUITID2 char(9), CONVCIRCUITID char(9), CONVCIRCUITID2 char(9), FEEDERINFO integer, INSTALLATIONDATE date, RETIREDATE date, NUMBEROFPHASES smallint, PHASEDESIGNATION integer, PHASINGVERIFIEDSTATUS char(30), SYMBOLROTATION double, INSTALLJOBPREFIX char(3), INSTALLJOBYEAR smallint, COMMENTS char(255), CEDSADEVICEID integer, LOCALOPOFFICE char(20), SOURCESIDEDEVICEID char(20), COMPLEXDEVICEIDC char(5), CUSTOMEROWNED char(5), SYMBOLNUMBER smallint, LOCDESC char(100),
      COUNTY smallint, ZIP char(10), GEMSDISTMAPNUM char(10), GEMSCIRCUITMAPNUM char(10), GEMSOTHERMAPNUM char(10), ANIMALGUARDTYPE char(5), DIVISION_ smallint, DISTRICT_ integer, VAULT char(6), REPLACEGUID guid, SUBTYPECD integer, INSTALLATIONTYPE char(5), LOCALOFFICEID char(4), REGION char(10), INSTALLJOBNUMBER char(14), CITY char(40), VERSIONNAME char(64), PROTECTIVESSD char(20), AUTOPROTECTIVESSD char(20), FEEDERTYPE_ smallint, SSDGUID char(38)
    -> ProcessTie
ProcessTie
    STATUS = @Value(STATUS)
    OUTPUT_FILE_NAME = $(output_file_name)
    FEEDERTYPE = @Value(FEEDERTYPE)
    output_file_name = unit_test_dwg
    UGUID = @Value(UGUID)
    CLIENTFEEDERTYPE = $(FEEDER_TYPE)
    UOID = @Value(UOID)
    CIRCUITIDS = $(CIRCUITIDS)
    CIRCUITID = @Value(CIRCUITID)
    SCHMCircuitID = 0
    -> SetTieBlockName_2
SetTieBlockName_2: AttributeCreator
    ATTR_LIST = autocad_block_name,"FME_CONDITIONAL:DEFAULT_VALUE'_FME_NO_OP_'BOOL_OP;AND;COMPOSITE_TEST;<Unused>;TEST @Value(SUBTYPECD) = 1;TEST @Value(STATUS) > 0'EECONDTIE'BOOL_OP;AND;COMPOSITE_TEST;<Unused>;TEST @Value(SUBTYPECD) = 4;TEST @Value(STATUS) > 0'EECTUG'BOOL_OP;AND;COMPOSITE_TEST;<Unused>;TEST @Value(SUBTYPECD) = 1;TEST @Value(STATUS) = 0'EECONDTIE'BOOL_OP;AND;COMPOSITE_TEST;<Unused>;TEST @Value(SUBTYPECD) = 4;TEST @Value(STATUS) = 0'PEECTUG'FME_NUM_CONDITIONS5___",autocad_layer,"FME_CONDITIONAL:DEFAULT_VALUE''BOOL_OP;AND;COMPOSITE_TEST;<Unused>;TEST @Value(SUBTYPE) = 1'MAP-ELEC-EXIST-DOH'BOOL_OP;AND;COMPOSITE_TEST;<Unused>;TEST @Value(SUBTYPE) = 4'MAP-ELEC-EXIST-DUG'FME_NUM_CONDITIONS3___",output_file_name,$(output_file_name),autocad_entity,autocad_insert
    -> SetDefaultPoint_3
Transformer (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, CIRCUITID char(9), OPERATINGVOLTAGE integer, INSTALLATIONTYPE char(5), SYMBOLNUMBER smallint, CONVERSIONID integer, OPERATINGNUMBER char(9), DISTRICT integer, DIVISION smallint, FEEDERTYPE smallint,
      DiagType char(48), DiagName char(48)
    -> ProcessTransformer_and_Anno [input 1]
EDGIS.TransformerSchem500Anno (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, FEATURECONVERSIONID integer, GLOBALID char(38), FEEDERTYPE smallint, SHAPE.AREA double, SHAPE.LEN double
    -> ProcessTransformer_and_Anno [input 2]
ProcessTransformer_and_Anno
    GEODB_TEXT_STRING = @Value(geodb_text_string)
    ANNOTATIONCLASSID = @Value(ANNOTATIONCLASSID)
    TEXTSTRING = @Value(TEXTSTRING)
    scale = $(scale)
    FONTNAME = @Value(FONTNAME)
    OPERATINGVOLTAGE = @Value(OPERATINGVOLTAGE)
    INSTALLATIONTYPE = @Value(INSTALLATIONTYPE)
    SYMBOLNUMBER = @Value(SYMBOLNUMBER)
    FME_GEOMETRY = @Value(fme_geometry)
    ROTATION = @Value(ROTATION)
    STATUS = @Value(STATUS)
    ITALIC = @Value(ITALIC)
    UOID = @Value(UOID)
    CIRCUITIDS = $(CIRCUITIDS)
    CLIENTOPERATINGVOLTAGE = $(VOLTAGE)
    FEATUREID = @Value(FEATUREID)
    FEEDERTYPE = @Value(FEEDERTYPE)
    SUBTYPE = @Value(SUBTYPE)
    BOLD = @Value(BOLD)
    ANGLE = @Value(ANGLE)
    UGUID = @Value(UGUID)
    CLIENTFEEDERTYPE = $(FEEDER_TYPE)
    YOFFSET = @Value(YOFFSET)
    CIRCUITID = @Value(CIRCUITID)
    Anno -> SetOutputFileLines_2
    Features -> SetDefaultPoint_3
VoltageRegulator (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, STATUS smallint, CIRCUITID char(9), OPERATINGVOLTAGE integer, SYMBOLNUMBER smallint, CONVERSIONID integer, OPERATINGNUMBER char(9), DISTRICT integer, DIVISION smallint, FEEDERTYPE smallint, DiagType char(48),
      DiagName char(48)
    -> ProcessVoltageRegulator_and_Anno [input 1]
ProcessVoltageRegulator_and_Anno
    output_file_name = $(output_file_name)
    GEODB_TEXT_STRING = @Value(geodb_text_string)
    ANNOTATIONCLASSID = @Value(ANNOTATIONCLASSID)
    scale = $(scale)
    FONTNAME = @Value(FONTNAME)
    OPERATINGVOLTAGE = @Value(OPERATINGVOLTAGE)
    SYMBOLNUMBER = @Value(SYMBOLNUMBER)
    FME_GEOMETRY = @Value(fme_geometry)
    STATUS = @Value(STATUS)
    ITALIC = @Value(ITALIC)
    XOFFSET = @Value(XOFFSET)
    UOID = @Value(UOID)
    CIRCUITIDS = $(CIRCUITIDS)
    CLIENTOPERATINGVOLTAGE = $(VOLTAGE)
    FEATUREID = @Value(FEATUREID)
    OBJECTID = @Value(OBJECTID)
    FEEDERTYPE = @Value(FEEDERTYPE)
    SUBTYPE = @Value(SUBTYPE)
    BOLD = @Value(BOLD)
    UGUID = @Value(UGUID)
    CLIENTFEEDERTYPE = $(FEEDER_TYPE)
    CIRCUITID = @Value(CIRCUITID)
    Features -> SetDefaultPoint_3
    Anno -> SetOutputFileLines_2
EDGIS.SubstationSchemAnno (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, GLOBALID char(38), SHAPE.AREA double, SHAPE.LEN double
    -> ProcessCity_3
ProcessCity_3: AttributeCreator
    ATTR_LIST = autocad_layer,MAP-LAND-MISC
    -> AnnotationToMText_2
AnnotationToMText_2
    XSCALE = .54
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> SetOutputFileLines_2
ServiceLocation (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, INITIALX double, INITIALY double, ROTATION double, UGUID guid, FEEDERTYPE smallint, DiagType char(48), DiagName char(48), STATUS smallint, GENCATEGORY smallint, LABELTEXT char(200), CIRCUITID char(9)
    -> ProcessServiceLocation
ProcessServiceLocation
    scale = $(scale)
    STATUS = @Value(STATUS)
    FEEDERTYPE = @Value(FEEDERTYPE)
    GENCATEGORY = @Value(GENCATEGORY)
    output_file_name = $(output_file_name)
    UGUID = @Value(UGUID)
    CLIENTFEEDERTYPE = $(FEEDER_TYPE)
    UOID = @Value(UOID)
    CIRCUITIDS = $(CIRCUITIDS)
    CIRCUITID = @Value(CIRCUITID)
    Feature -> SetDefaultPoint_3
    Feature -> LabelAdderAndOffsetter
SetDefaultPoint_3: AttributeCreator
    ATTR_LIST = output_file_name,$(output_file_name),autocad_entity,autocad_insert,autocad_linetype,ByBlock
    -> RotateToCAD_2
RotateToCAD_2
    SYMBOLROTATION = @Value(ROTATION)
    RotateToCADTemplate_Output -> SetScale_2
LabelAdderAndOffsetter
    scale = $(scale)
    LABELTEXT = @Value(LABELTEXT)
    FME_GEOMETRY = @Value(fme_geometry)
    -> SetScale_2
SetScale_2
    scale = $(scale)
    SetScaleFromScaleFactor_Output -> SetOutputFileName_3
SetOutputFileName_3
    output_file_name = $(output_file_name)
    SetOutputFileName_Output_1 -> SetOutputFileLines_2
SetOutputFileLines_2: AttributeCreator
    ATTR_LIST = output_file_name,$(output_file_name)
    -> MAP-ELEC-EXIST-DUG (writer REALDWG_1)
MAP-ELEC-EXIST-DUG (writer REALDWG_1)
    attributes: OBJECTID number(12,10), SCHEMATICTID char(128), CIRCUITID char(9), GLOBALID char(40)
EST-ELEC-EXIST-DUG (writer REALDWG_1) [off]
    attributes: OBJECTID number(12,10), SCHEMATICTID char(128), CIRCUITID char(9), GLOBALID char(40)

Bookmark: Schematic Lines
DistBusBar (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, FROMTID char(128), TOTID char(128), FROMPORT integer, TOPORT integer, FLOWDIRECTION integer, UGUID guid, STATUS smallint, CIRCUITID char(9), OPERATINGVOLTAGE integer, DISTRICT integer, DIVISION smallint, FEEDERTYPE smallint, DiagType char(48), DiagName char(48),
      SHAPE_Length double
    -> ProcessBusBar_2
ProcessBusBar_2
    STATUS = @Value(STATUS)
    SCHEMATICTID = @Value(SCHEMATICTID)
    OUTPUT_FILE_NAME = schm_to_cad
    OPERATINGVOLTAGE = @Value(OPERATINGVOLTAGE)
    SUBTYPE = @Value(SUBTYPE)
    FEEDERTYPE = @Value(FEEDERTYPE)
    UGUID = @Value(UGUID)
    CLIENTFEEDERTYPE = $(FEEDER_TYPE)
    UOID = @Value(UOID)
    CIRCUITIDS = $(CIRCUITIDS)
    CLIENTOPERATINGVOLTAGE = $(VOLTAGE)
    CIRCUITID = @Value(CIRCUITID)
    SCHMCircuitID = 0
    ProcessBusBar_Output_1 -> Clipper [input 2]
PriOHConductor (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, FROMTID char(128), TOTID char(128), FROMPORT integer, TOPORT integer, FLOWDIRECTION integer, UGUID guid, LABELTEXT2 char(100), STATUS smallint, CIRCUITID char(9), OPERATINGVOLTAGE integer, CONVERSIONID char(9), DISTRICT integer, DIVISION smallint, SUBTYPECD integer,
      WINDSPEEDCODE smallint, CONVCIRCUITID char(9), CIRCUITCOLOR char(50), FEEDERTYPE smallint, DiagType char(48), DiagName char(48), SHAPE_Length double
    -> ProcessPrimaryOH_and_Anno
ProcessPrimaryOH_and_Anno
    CLIENTOPERATINGVOLTAGE = $(VOLTAGE)
    CIRCUITCOLOR = @Value(CIRCUITCOLOR)
    scale = $(scale)
    STATUS = @Value(STATUS)
    SCHEMATICTID = @Value(SCHEMATICTID)
    OPERATINGVOLTAGE = @Value(OPERATINGVOLTAGE)
    FEEDERTYPE = @Value(FEEDERTYPE)
    SUBTYPE = @Value(SUBTYPE)
    UGUID = @Value(UGUID)
    CLIENTFEEDERTYPE = $(FEEDER_TYPE)
    UOID = @Value(UOID)
    CIRCUITIDS = $(CIRCUITIDS)
    LABELTEXT2 = @Value(LABELTEXT2)
    CIRCUITID = @Value(CIRCUITID)
    SCHMCircuitID = 0
    Features -> Clipper [input 2]
    Anno -> Clipper [input 2]
PriUGConductor (reader GEODATABASE_FILE_1)
    attributes: geodb_oid integer, OBJECTID integer, DIAGRAMCLASSID integer, DIAGRAMOBJECTID integer, SCHEMATICTID char(128), ISINITIAL integer, ISDISPLAYED integer, RELATIONOBJECTID integer, RELATIONCLASSID integer, DATASOURCEID integer, UCID integer, UOID integer, USID integer, UPDATESTATUS integer, SUBTYPE integer, PROPERTYSET blob, FROMTID char(128), TOTID char(128), FROMPORT integer, TOPORT integer, FLOWDIRECTION integer, UGUID guid, LABELTEXT2 char(100), STATUS smallint, CIRCUITID char(9), OPERATINGVOLTAGE integer, CONVERSIONID integer, DISTRICT integer, DIVISION smallint, SUBTYPECD integer,
      CONVCIRCUITID char(9), CIRCUITCOLOR char(50), FEEDERTYPE smallint, DiagType char(48), DiagName char(48), SHAPE_Length double
    -> ProcessPrimaryUG_and_Anno
ProcessPrimaryUG_and_Anno
    CLIENTOPERATINGVOLTAGE = $(VOLTAGE)
    CIRCUITCOLOR = @Value(CIRCUITCOLOR)
    scale = $(scale)
    STATUS = @Value(STATUS)
    SCHEMATICTID = @Value(SCHEMATICTID)
    OPERATINGVOLTAGE = @Value(OPERATINGVOLTAGE)
    FEEDERTYPE = @Value(FEEDERTYPE)
    SUBTYPE = @Value(SUBTYPE)
    UGUID = @Value(UGUID)
    CLIENTFEEDERTYPE = $(FEEDER_TYPE)
    UOID = @Value(UOID)
    CIRCUITIDS = $(CIRCUITIDS)
    LABELTEXT2 = @Value(LABELTEXT2)
    CIRCUITID = @Value(CIRCUITID)
    SCHMCircuitID = 0
    Features -> Clipper [input 2]
    Anno -> Clipper [input 2]
Clipper
    CREATE_AGGREGATES = No
    MERGE_ATTRS = No
    PRESERVE_CLIPPEE_EXTENTS = No
    CLIP_TYPE = Multiple Clippers
    BOUNDARY_CASES = Treat as Inside
    INSIDE -> SetOutputFileLines
    CLIPPED_INSIDE -> SetOutputFileLines
SetOutputFileLines: AttributeCreator
    ATTR_LIST = output_file_name,$(output_file_name),autocad_linetype_generation,1
    -> EST-ELEC-CIRCOH (writer REALDWG_1)
EST-ELEC-CIRCOH (writer REALDWG_1)
    attributes: OBJECTID number(12,10), GLOBALID char(40), SCHEMATICTID char(40)

Bookmark: Landbase
LBGIS.railways (reader GEODATABASE_SDE_2)
    attributes: geodb_oid integer, OBJECTID integer, FEATTYP integer, NAME char(100), NAMELC char(3), F_ELEV integer, T_ELEV integer, DISPCLASS integer, PARTSTRUC integer, STATE char(35), SHAPE.LEN double
    -> ProcessRailways
ProcessRailways: AttributeCreator
    ATTR_LIST = autocad_linetype,ELRR,autocad_layer,MAP-LAND-MISC,autocad_entity,autocad_line
    -> Clipper_2 [input 2]
LBGIS.waterseg (reader GEODATABASE_SDE_2)
    attributes: geodb_oid integer, OBJECTID integer, ID char(15), FEATTYP integer, TYP integer, METERS double, NAME char(70), NAMELC char(3), DISPCLASS integer, STATE char(35), SHAPE.LEN double
    -> ProcessWaterP_and_Seg_2 [input 1]
LBGIS.waterp (reader GEODATABASE_SDE_2)
    attributes: geodb_oid integer, OBJECTID integer, ID char(15), FEATTYP integer, TYP integer, FEATAREA double, FEATPERIM double, NAME char(70), NAMELC char(3), DISPCLASS integer, STATE char(35), SHAPE.AREA double, SHAPE.LEN double
    -> ProcessWaterP_and_Seg_2 [input 2]
ProcessWaterP_and_Seg_2
    scale = $(scale)
    output_file_name = $(output_file_name)
    NAME = @Value(NAME)
    Features -> DonutRemover_2
    Labels -> IntersectSpatialFilter [input 2]
DonutRemover_2
    FME_GEOMETRY = @Value(fme_geometry)
    DonutParts -> Clipper_3 [input 2]
    NotDonut -> Clipper_3 [input 2]
Clipper_3
    CREATE_AGGREGATES = No
    MERGE_ATTRS = No
    PRESERVE_CLIPPEE_EXTENTS = No
    CLIP_TYPE = Multiple Clippers
    BOUNDARY_CASES = Treat as Inside
    INSIDE -> SetOutputFileName_2
    CLIPPED_INSIDE -> SetOutputFileName_2
    CLIPPED_OUTSIDE -> SetOutputFileName_2
IntersectSpatialFilter: SpatialFilter
    USE_BOUNDING_BOX = No
    MERGE_ATTRS = No
    BASE_TYPE = Multiple Filters
    PASS_CRITERIA = Pass Against One Filter
    PREDATTR = _predicate
    PREDICATES = INTERSECTS
    CURVE_BOUNDARY_RULE_PARAM = Default Rule
    PASSED -> MAP-LAND-MISC (writer REALDWG_1)
LBGIS.streets_ca (reader GEODATABASE_SDE_2)
    attributes: geodb_oid integer, OBJECTID integer, ID char(15), FEATTYP integer, FT integer, F_JNCTID char(15), F_JNCTTYP integer, T_JNCTID char(15), T_JNCTTYP integer, PJ integer, METERS double, FRC integer, NETCLASS integer, NETBCLASS integer, NET2CLASS integer, SOL integer, NAMETYP integer, CHARGE char(2), SHIELDNUM char(10), RTETYP integer, RTEDIR char(2), RTEDIRVD char(2), PROCSTAT integer, FOW integer, SLIPRD integer, FREEWAY integer, BACKRD integer, TOLLRD integer, RDCOND integer, STUBBLE integer,
      PRIVATERD integer, CONSTATUS char(2), ONEWAY char(2), F_BP integer, T_BP integer, F_ELEV integer, T_ELEV integer, KPH integer, MINUTES double, POSACCUR integer, CARRIAGE char(1), LANES integer, RAMP integer, ADA integer, TRANS integer, DYNSPEED integer, SPEEDCAT integer, NTHRUTRAF integer, ROUGHRD integer, PARTSTRUC integer, STATE char(35), FULLNAME char(100), PREFIX char(10), PRETYPE char(30), NAME char(100), TYPE char(20), SUFFIX char(10), NAME_DIR char(2), NAMELC char(3), FULLNAME1 char(100),
      PREFIX1 char(10), PRETYPE1 char(30), NAME1 char(100), TYPE1 char(20), SUFFIX1 char(10), NAME_DIR1 char(2), NAMELC1 char(3), FULLNAME2 char(100), PREFIX2 char(10), PRETYPE2 char(30), NAME2 char(100), TYPE2 char(20), SUFFIX2 char(10), NAME_DIR2 char(2), NAMELC2 char(3), FULLNAME3 char(100), PREFIX3 char(10), PRETYPE3 char(30), NAME3 char(100), TYPE3 char(20), SUFFIX3 char(10), NAME_DIR3 char(2), NAMELC3 char(3), FULLNAME4 char(100), PREFIX4 char(10), PRETYPE4 char(30), NAME4 char(100), TYPE4 char(20), SUFFIX4 char(10), NAME_DIR4 char(2),
      NAMELC4 char(3), FULLNAME5 char(100), PREFIX5 char(10), PRETYPE5 char(30), NAME5 char(100), TYPE5 char(20), SUFFIX5 char(10), NAME_DIR5 char(2), NAMELC5 char(3), FT_RESTR_02 char(1), TF_RESTR_02 char(1), FT_RESTR_04 char(1), TF_RESTR_04 char(1), FT_RESTR_05 char(1), TF_RESTR_05 char(1), FT_RESTR_06 char(1), TF_RESTR_06 char(1), FT_RESTR_07 char(1), TF_RESTR_07 char(1), FT_RESTR_09 char(1), TF_RESTR_09 char(1), FT_RESTR_10 char(1), TF_RESTR_10 char(1), FT_DIR char(2), TF_DIR char(2), MPH_GRP integer, MSTIMEZONE integer, ROAD_CL integer, RENDER_CL integer, FULLSHIELD char(55),
      SHIELD char(50), SHIELD_DIR char(2), SHIELD_CL integer, SHIELD_MASK char(20), SHIELD_LBL char(4), FT_RCAT_DA_50_1 double, TF_RCAT_DA_50_1 double, FT_RCAT_DB_50_1 double, TF_RCAT_DB_50_1 double, FT_RCAT_DG_50_1 double, TF_RCAT_DG_50_1 double, FT_RCAT_DI_50_1 double, TF_RCAT_DI_50_1 double, FT_RCAT_DO_50_1 double, TF_RCAT_DO_50_1 double, FT_RCAT_DP_50_1 double, TF_RCAT_DP_50_1 double, FT_RCAT_LH_50_1 char(1), TF_RCAT_LH_50_1 char(1), FT_RCAT_LH_50_4 char(1), TF_RCAT_LH_50_4 char(1), FT_RCAT_LI_50_1 char(1), TF_RCAT_LI_50_1 char(1), FT_RCAT_LI_50_4 char(1), TF_RCAT_LI_50_4 char(1), FT_RCAT_LJ_50_1 char(1), TF_RCAT_LJ_50_1 char(1), FT_RCAT_LJ_50_4 char(1), TF_RCAT_LJ_50_4 char(1), FT_RCAT_LK_50_1 char(1),
      TF_RCAT_LK_50_1 char(1), FT_RCAT_LK_50_4 char(1), TF_RCAT_LK_50_4 char(1), FT_RCAT_LL_50_1 char(1), TF_RCAT_LL_50_1 char(1), FT_RCAT_LL_50_4 char(1), TF_RCAT_LL_50_4 char(1), FT_RCAT_LM_50_1 char(1), TF_RCAT_LM_50_1 char(1), FT_RCAT_LM_50_4 char(1), TF_RCAT_LM_50_4 char(1), FT_RCAT_LN_50_1 char(1), TF_RCAT_LN_50_1 char(1), FT_RCAT_LN_50_4 char(1), TF_RCAT_LN_50_4 char(1), FT_RCAT_LO_50_1 char(1), TF_RCAT_LO_50_1 char(1), FT_RCAT_LO_50_4 char(1), TF_RCAT_LO_50_4 char(1), FT_RCAT_LP_50_1 char(1), TF_RCAT_LP_50_1 char(1), FT_RCAT_LP_50_4 char(1), TF_RCAT_LP_50_4 char(1), FT_RCAT_LQ_50_1 char(1), TF_RCAT_LQ_50_1 char(1), FT_RCAT_LQ_50_4 char(1), TF_RCAT_LQ_50_4 char(1), FT_RCAT_LZ_50_1 char(1), TF_RCAT_LZ_50_1 char(1), FT_RCAT_LZ_50_4 char(1),
      TF_RCAT_LZ_50_4 char(1), FT_RCAT_LHAZ_50_1 char(1), TF_RCAT_LHAZ_50_1 char(1), FT_RCAT_LHAZ_50_4 char(1), TF_RCAT_LHAZ_50_4 char(1), RCAT_PREFERRED_1 char(1), RCAT_PREFERRED_3 char(1), RCAT_PREFERRED_4 char(1), RCAT_RESTRICTED_1 char(1), RCAT_RESTRICTED_3 char(1), SHAPE.LEN double
    -> Process_CA_Street_Names [input 2]
Note: OLD
Process_CA_Street_Names: Process CA Street Names
    scale = $(scale)
    OBJECTID = @Value(OBJECTID)
    SHIELDNUM = @Value(SHIELDNUM)
    FULLNAME = @Value(FULLNAME)
    -> Clipper_2 [input 2]
LBGIS.City (reader GEODATABASE_SDE_2)
    attributes: geodb_oid integer, OBJECTID integer, FIPSSTCO char(5), STATE char(30), COUNTY char(66), CITY_NAME char(30), CITY_TYPE char(30), ST_PL_FIPS char(10), PL_FIPS char(5), CLASS_CODE char(5), INC_FLAG char(5), TA_NAME char(50), TA_FIPS char(10), DT_ANX char(6), DT_UPD char(6), DT_VRF char(6), ST_FILING char(15), SPD_TAX char(5), ST_UTL_SER char(5), UTL_SP_TAX char(5), UTL_TA_NAM char(50), UTL_TA_FIP char(10), UTL_FILING char(15), UTL_SPD_TX char(5), GNIS_CODE char(15), SOURCE char(25), BOE_TYPE char(25), BOE_NUM char(10), PLACEFIP char(5), TOT_CODE char(3),
      TOT_NAME char(50), TOT_STATUS char(6), PGESOURCE char(150), SHAPE.AREA double, SHAPE.LEN double
    -> ProcessCity
ProcessCity: AttributeCreator
    ATTR_LIST = autocad_linetype,ELCITYB,autocad_layer,MAP-LAND-MISC,autocad_entity,autocad_line
    -> DonutRemover
DonutRemover
    FME_GEOMETRY = @Value(fme_geometry)
    DonutParts -> GeometryCoercer_2
    NotDonut -> GeometryCoercer_2
GeometryCoercer_2
    KIND = fme_line
    COERCED -> Clipper_2 [input 2]
Clipper_2
    CREATE_AGGREGATES = No
    MERGE_ATTRS = No
    PRESERVE_CLIPPEE_EXTENTS = No
    CLIP_TYPE = Multiple Clippers
    BOUNDARY_CASES = Treat as Inside
    INSIDE -> SetOutputFileName_2
    CLIPPED_INSIDE -> SetOutputFileName_2
SetOutputFileName_2
    output_file_name = $(output_file_name)
    SetOutputFileName_Output_1 -> MAP-LAND-MISC (writer REALDWG_1)
EDGIS.SchemStreetAnno500 (reader GEODATABASE_SDE_1)
    attributes: geodb_oid integer, OBJECTID integer, FEATUREID integer, ZORDER integer, ANNOTATIONCLASSID integer, SYMBOLID integer, STATUS smallint, TEXTSTRING char(255), FONTNAME char(255), FONTSIZE double, BOLD smallint, ITALIC smallint, UNDERLINE smallint, VERTICALALIGNMENT smallint, HORIZONTALALIGNMENT smallint, XOFFSET double, YOFFSET double, ANGLE double, FONTLEADING double, WORDSPACING double, CHARACTERWIDTH double, CHARACTERSPACING double, FLIPANGLE double, OVERRIDE integer, SHAPE.AREA double, SHAPE.LEN double
    -> ProcessCity_2
ProcessCity_2: AttributeCreator
    ATTR_LIST = autocad_layer,MAP-LAND-MISC
    -> AnnotationToMText_4
AnnotationToMText_4
    XSCALE = .54
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> MAP-LAND-MISC (writer REALDWG_1)
MAP-LAND-MISC (writer REALDWG_1)
    attributes: OBJECTID number(12,10)

FME custom transformer ProcessPrimaryUG_and_Anno

Parameters:
- STATUS = @Value(STATUS)   # Status
- CIRCUITID = @Value(CIRCUITID)   # Circuitid
- SCHEMATICTID = @Value(SCHEMATICTID)   # Schematictid
- UOID = @Value(UOID)   # Uoid
- SUBTYPE = @Value(SUBTYPE)   # Subtype
- UGUID = @Value(UGUID)   # Uguid
- CIRCUITCOLOR = @Value(CIRCUITCOLOR)   # Circuitcolor
- SCHMCircuitID = 0
- CIRCUITIDS = @Value(CircuitIds)   # Circuitids
- scale =   # Scale
- LABELTEXT2 = @Value(LABELTEXT2)   # Labeltext2
- OPERATINGVOLTAGE = @Value(OPERATINGVOLTAGE)   # Operatingvoltage
- FEEDERTYPE = @Value(FEEDERTYPE)   # Feedertype
- CLIENTOPERATINGVOLTAGE = @Value(clientOperatingVoltage)   # Clientoperatingvoltage
- CLIENTFEEDERTYPE = @Value(clientFeederType)   # Clientfeedertype

SetPrimaryUGLineAttributes_Input (input)
    -> AttributeRenamer
AttributeRenamer
    ATTR_LIST = UOID,OBJECTID,"",UGUID,GLOBALID,""
    -> Tester_3
Tester_3
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> LineJoiner
    PASSED -> Tester_CircuitID_2
Tester_CircuitID_2
    TEST_MODE = Automatic
    TEST_DESCRIPTION = ""
    BOOL_OP = OR
    TEST_CLAUSE = TEST $(SCHMCircuitID) = 0
    PASSED -> LineTypeSetPrimaryOH_Circuit
    FAILED -> Tester_CircuitID
Tester_CircuitID
    TEST_MODE = Automatic
    TEST_DESCRIPTION = ""
    COMPOSITE_TEST = 1
    BOOL_OP = COMPOSITE
    TEST_CLAUSE = TEST @Value(CIRCUITID) = $(SCHMCircuitID)
    PASSED -> LineTypeSetPrimaryOH_Circuit
LineTypeSetPrimaryOH_Circuit: AttributeCreator
    ATTR_LIST = autocad_linetype,"FME_CONDITIONAL:DEFAULT_VALUE'_FME_NO_OP_'BOOL_OP;OR;COMPOSITE_TEST;<Unused>;TEST @Value(SUBTYPE) = 1'EECIRCU1'BOOL_OP;OR;COMPOSITE_TEST;<Unused>;TEST @Value(SUBTYPE) = 3'EECIRCU3'BOOL_OP;OR;COMPOSITE_TEST;<Unused>;TEST @Value(SUBTYPE) = 2'EECIRCU1'FME_NUM_CONDITIONS4___",autocad_layer,MAP-ELEC-CIRCUG,autocad_true_color,"FME_CONDITIONAL:DEFAULT_VALUE'_FME_NO_OP_'BOOL_OP;OR;COMPOSITE_TEST;<Unused>;TEST @Value(CIRCUITCOLOR) = Green'51,160,44'BOOL_OP;OR;COMPOSITE_TEST;<Unused>;TEST @Value(CIRCUITCOLOR) = Pastel Red'251,154,153'BOOL_OP;OR;COMPOSITE_TEST;<Unused>;TEST @Value(CIRCUITCOLOR) = Yellow'255,237,111'BOOL_OP;OR;COMPOSITE_TEST;<Unused>;TEST @Value(CIRCUITCOLOR) = Dark Blue'5,47,227'BOOL_OP;OR;COMPOSITE_TEST;<Unused>;TEST @Value(CIRCUITCOLOR) = Ginger Pink'255,0,197'BOOL_OP;OR;COMPOSITE_TEST;<Unused>;TEST @Value(CIRCUITCOLOR) = Purple'106,61,154'BOOL_OP;OR;COMPOSITE_TEST;<Unused>;TEST @Value(CIRCUITCOLOR) = Blue'31,120,180'BOOL_OP;OR;COMPOSITE_TEST;<Unused>;TEST @Value(CIRCUITCOLOR) = Dark Pastel Red'251,128,114'BOOL_OP;OR;COMPOSITE_TEST;<Unused>;TEST @Value(CIRCUITCOLOR) = Brown'177,89,40'BOOL_OP;OR;COMPOSITE_TEST;<Unused>;TEST @Value(CIRCUITCOLOR) = Light Purple'188,128,189'BOOL_OP;OR;COMPOSITE_TEST;<Unused>;TEST @Value(CIRCUITCOLOR) = Orange'255,127,0'BOOL_OP;OR;COMPOSITE_TEST;<Unused>;TEST @Value(CIRCUITCOLOR) = Lime Green'179,222,105'BOOL_OP;OR;COMPOSITE_TEST;<Unused>;TEST @Value(CIRCUITCOLOR) = Pastel Blue'166,206,227'BOOL_OP;OR;COMPOSITE_TEST;<Unused>;TEST @Value(CIRCUITCOLOR) = Pink'252,205,229'BOOL_OP;OR;COMPOSITE_TEST;<Unused>;TEST @Value(CIRCUITCOLOR) = Pastel Green'178,223,138'BOOL_OP;OR;COMPOSITE_TEST;<Unused>;TEST @Value(CIRCUITCOLOR) = Dark Pastel Purple'190,186,218'BOOL_OP;OR;COMPOSITE_TEST;<Unused>;TEST @Value(CIRCUITCOLOR) = Pastel Orange'253,191,111'BOOL_OP;OR;COMPOSITE_TEST;<Unused>;TEST @Value(CIRCUITCOLOR) = Light Pastel Green'204,235,197'BOOL_OP;OR;COMPOSITE_TEST;<Unused>;TEST @Value(CIRCUITCOLOR) = Pastel Purple'202,178,214'BOOL_OP;OR;COMPOSITE_TEST;<Unused>;TEST @Value(CIRCUITCOLOR) = Grey'217,217,217'FME_NUM_CONDITIONS21___",autocad_entity,autocad_line
    -> Features (output)
Features (output)
LineJoiner
    GROUP_BY = CIRCUITID SUBTYPE CIRCUITCOLOR LABELTEXT2
    GROUP_BREAK = no
    PRESERVE = no
    TOPOLOGY = End noded
    LINES_AS_SEGMENTS = No
    CONSIDER_NODE_ELEVATION = no
    BREAK = no
    LINE -> Labeller_2
Labeller_2
    SPOT_CHOICE = Above or Right
    ENDS = no
    AVERAGE_CHAR_WIDTH = 0.0
    LABATTR = @Value(LABELTEXT2)
    HEIGHT = 30
    SPACE = 0
    TANROTATTR = _label_rotation
    PARROTATTR = _parallel_rotation
    OVERLAPS = Yes
    DIST = 20
    MIN = 0
    LABEL -> AnnotationToMText_DCR
AnnotationToMText_DCR
    XSCALE = .54
    fme_geometry = 1
    FONTNAME = 1
    YSCALE = .54
    BOLD = 1
    ITALIC = 1
    GEODB_TEXT_STRING = @Value(LABELTEXT2)
    SCALE = $(scale)
    Tester_Passed -> AttributeCreator
AttributeCreator
    ATTR_LIST = autocad_color,ByBlock,autocad_linetype,ByBlock,autocad_layer,MAP-ELEC-CIRCUG
    -> Anno (output)
Anno (output)
Labeller [off]
    SPOT_CHOICE = Above or Right
    ENDS = no
    AVERAGE_CHAR_WIDTH = 0.0
    LABATTR = @Value(LABELTEXT2)
    HEIGHT = 1
    SPACE = 2000
    TANROTATTR = _label_rotation
    PARROTATTR = _parallel_rotation
    OVERLAPS = Yes
    DIST = 1
    MIN = 0
LabelPointReplacer [off]
    ALWAYSROTATE = yes
    LABATTR = @Value(LABELTEXT2)
    HEIGHT = 8

FME custom transformer CreateSearchPolygon

Parameters:
- _GEODBInSearchFeature_GEODATABASE_SDE = 2812758 12845426 2812758 12845734 2813337 12845734 2813337 12845426 2812758 12845426   # Search Feature

Creator
    NUM = 1
    GEOMTYPE = Geometry Object
    CREATED -> AttributeCreator_2
AttributeCreator_2
    ATTR_LIST = OriginalCoordinatesSSV,$(_GEODBInSearchFeature_GEODATABASE_SDE)
    -> PythonCaller
PythonCaller
    PYTHONSOURCE:
      import fmeobjects
      # Template Function interface:
      def processFeature(feature):
          originalCoordinatesSSV = feature.getAttribute("OriginalCoordinatesSSV")

      #get x and ys
          i = 1
          coords = []
          x = []
          y = []
          xys = originalCoordinatesSSV.split()
          if len(xys) < 5 or len(xys) % 2 != 0:   raise Exception("Need >5 coords and even number!")
          for x_or_y in xys:
              if i % 2 == 0:
                  y.append(x_or_y)
              else:
                  x.append(x_or_y)
              i = i + 1

      #get coords
          for index, x_value in enumerate(x):
              coords.append((float(x_value), float(y[index])))

          boundary = fmeobjects.FMELine(coords)
          polygon = fmeobjects.FMEPolygon(boundary)
          feature.setGeometry(polygon)

      # Template Class Interface:
      class FeatureProcessor(object):
          def __init__(self):
              pass
          def input(self,feature):
              self.pyoutput(feature)
          def close(self):
              pass
    PYTHONSYMBOL = processFeature
    -> PythonCaller_Output (output)
PythonCaller_Output (output)

FME custom transformer SetSwitchLayer

Parameters:
- SUBTYPE = @Value(SUBTYPE)   # Subtype

Input (input)
    -> SetLayerNameOHUG_2
SetLayerNameOHUG_2: AttributeCreator
    ATTR_LIST = autocad_layer,"FME_CONDITIONAL:DEFAULT_VALUE'_FME_NO_OP_'BOOL_OP;AND;COMPOSITE_TEST;<Unused>;TEST @Value(SUBTYPE) IN 1,2,6,7'MAP-ELEC-EXIST-DOH'BOOL_OP;AND;COMPOSITE_TEST;<Unused>;TEST @Value(SUBTYPE) IN 3,4,5'MAP-ELEC-EXIST-DUG'FME_NUM_CONDITIONS3___"
    -> Output (output)
Output (output)

FME custom transformer ProcessPrimaryOH_and_Anno

Parameters:
- STATUS = @Value(STATUS)   # Status
- CIRCUITID = @Value(CIRCUITID)   # Circuitid
- UOID = @Value(UOID)   # Uoid
- SUBTYPE = @Value(SUBTYPE)   # Subtype
- UGUID = @Value(UGUID)   # Uguid
- SCHEMATICTID = @Value(SCHEMATICTID)   # Schematictid
- CIRCUITCOLOR = @Value(CIRCUITCOLOR)   # Circuitcolor
- SCHMCircuitID = 0
- CIRCUITIDS = @Value(CircuitIds)   # Circuitids
- scale =   # Scale
- LABELTEXT2 = @Value(LABELTEXT2)   # Labeltext2
- OPERATINGVOLTAGE = @Value(OPERATINGVOLTAGE)   # Operatingvoltage
- FEEDERTYPE = @Value(FEEDERTYPE)   # Feedertype
- CLIENTFEEDERTYPE = @Value(clientFeederType)   # Clientfeedertype
- CLIENTOPERATINGVOLTAGE = @Value(clientOperatingVoltage)   # Clientoperatingvoltage

LineTypeSetPrimaryOH_Input (input)
    -> AttributeRenamer
AttributeRenamer
    ATTR_LIST = UOID,OBJECTID,"",UGUID,GLOBALID,""
    -> Tester_3
Tester_3
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> Tester_CircuitID_2
    PASSED -> LineJoiner
Tester_CircuitID_2
    TEST_MODE = Automatic
    TEST_DESCRIPTION = ""
    BOOL_OP = OR
    TEST_CLAUSE = TEST $(SCHMCircuitID) = 0
    PASSED -> LineTypeSetPrimaryOH_Circuit_2
    FAILED -> Tester_CircuitID
Tester_CircuitID
    TEST_MODE = Automatic
    TEST_DESCRIPTION = ""
    COMPOSITE_TEST = 1
    BOOL_OP = COMPOSITE
    TEST_CLAUSE = TEST @Value(CIRCUITID) = $(SCHMCircuitID)
    PASSED -> LineTypeSetPrimaryOH_Circuit_2
LineTypeSetPrimaryOH_Circuit_2: AttributeCreator
    ATTR_LIST = autocad_linetype,"FME_CONDITIONAL:DEFAULT_VALUE'_FME_NO_OP_'BOOL_OP;OR;COMPOSITE_TEST;<Unused>;TEST @Value(SUBTYPE) = 1'EECIRCO1'BOOL_OP;OR;COMPOSITE_TEST;<Unused>;TEST @Value(SUBTYPE) = 3'EECIRCO3'BOOL_OP;OR;COMPOSITE_TEST;<Unused>;TEST @Value(SUBTYPE) = 2'EECIRCO1'FME_NUM_CONDITIONS4___",autocad_layer,MAP-ELEC-CIRCOH,autocad_true_color,"FME_CONDITIONAL:DEFAULT_VALUE'_FME_NO_OP_'BOOL_OP;OR;COMPOSITE_TEST;<Unused>;TEST @Value(CIRCUITCOLOR) = Green'51,160,44'BOOL_OP;OR;COMPOSITE_TEST;<Unused>;TEST @Value(CIRCUITCOLOR) = Pastel Red'251,154,153'BOOL_OP;OR;COMPOSITE_TEST;<Unused>;TEST @Value(CIRCUITCOLOR) = Yellow'255,237,111'BOOL_OP;OR;COMPOSITE_TEST;<Unused>;TEST @Value(CIRCUITCOLOR) = Dark Blue'5,47,227'BOOL_OP;OR;COMPOSITE_TEST;<Unused>;TEST @Value(CIRCUITCOLOR) = Ginger Pink'255,0,197'BOOL_OP;OR;COMPOSITE_TEST;<Unused>;TEST @Value(CIRCUITCOLOR) = Purple'106,61,154'BOOL_OP;OR;COMPOSITE_TEST;<Unused>;TEST @Value(CIRCUITCOLOR) = Blue'31,120,180'BOOL_OP;OR;COMPOSITE_TEST;<Unused>;TEST @Value(CIRCUITCOLOR) = Dark Pastel Red'251,128,114'BOOL_OP;OR;COMPOSITE_TEST;<Unused>;TEST @Value(CIRCUITCOLOR) = Brown'177,89,40'BOOL_OP;OR;COMPOSITE_TEST;<Unused>;TEST @Value(CIRCUITCOLOR) = Light Purple'188,128,189'BOOL_OP;OR;COMPOSITE_TEST;<Unused>;TEST @Value(CIRCUITCOLOR) = Orange'255,127,0'BOOL_OP;OR;COMPOSITE_TEST;<Unused>;TEST @Value(CIRCUITCOLOR) = Lime Green'179,222,105'BOOL_OP;OR;COMPOSITE_TEST;<Unused>;TEST @Value(CIRCUITCOLOR) = Pastel Blue'166,206,227'BOOL_OP;OR;COMPOSITE_TEST;<Unused>;TEST @Value(CIRCUITCOLOR) = Pink'252,205,229'BOOL_OP;OR;COMPOSITE_TEST;<Unused>;TEST @Value(CIRCUITCOLOR) = Pastel Green'178,223,138'BOOL_OP;OR;COMPOSITE_TEST;<Unused>;TEST @Value(CIRCUITCOLOR) = Dark Pastel Purple'190,186,218'BOOL_OP;OR;COMPOSITE_TEST;<Unused>;TEST @Value(CIRCUITCOLOR) = Pastel Orange'253,191,111'BOOL_OP;OR;COMPOSITE_TEST;<Unused>;TEST @Value(CIRCUITCOLOR) = Light Pastel Green'204,235,197'BOOL_OP;OR;COMPOSITE_TEST;<Unused>;TEST @Value(CIRCUITCOLOR) = Pastel Purple'202,178,214'BOOL_OP;OR;COMPOSITE_TEST;<Unused>;TEST @Value(CIRCUITCOLOR) = Grey'217,217,217'FME_NUM_CONDITIONS21___",autocad_entity,autocad_line
    -> Features (output)
Features (output)
LineJoiner
    GROUP_BY = CIRCUITID SUBTYPE CIRCUITCOLOR LABELTEXT2
    GROUP_BREAK = no
    PRESERVE = no
    TOPOLOGY = End noded
    LINES_AS_SEGMENTS = No
    CONSIDER_NODE_ELEVATION = no
    BREAK = no
    LINE -> Labeller_2
Labeller_2
    SPOT_CHOICE = Above or Right
    ENDS = no
    AVERAGE_CHAR_WIDTH = 0.0
    LABATTR = @Value(LABELTEXT2)
    HEIGHT = 30
    SPACE = 0
    TANROTATTR = _label_rotation
    PARROTATTR = _parallel_rotation
    OVERLAPS = Yes
    DIST = 20
    MIN = 0
    LABEL -> AnnotationToMText_DCR
AnnotationToMText_DCR
    XSCALE = .54
    fme_geometry = 1
    FONTNAME = 1
    YSCALE = .54
    BOLD = 1
    ITALIC = 1
    GEODB_TEXT_STRING = @Value(LABELTEXT2)
    SCALE = $(scale)
    Tester_Passed -> AttributeCreator
AttributeCreator
    ATTR_LIST = autocad_color,ByBlock,autocad_linetype,ByBlock,autocad_layer,MAP-ELEC-CIRCOH
    -> Anno (output)
Anno (output)
LabelPointReplacer [off]
    ALWAYSROTATE = yes
    LABATTR = @Value(LABELTEXT2)
    HEIGHT = 8
Labeller [off]
    SPOT_CHOICE = Above or Right
    ENDS = no
    AVERAGE_CHAR_WIDTH = 0.0
    LABATTR = @Value(LABELTEXT2)
    HEIGHT = 1
    SPACE = 2000
    TANROTATTR = _label_rotation
    PARROTATTR = _parallel_rotation
    OVERLAPS = Yes
    DIST = 1
    MIN = 0

FME custom transformer ProcessPrimary

Parameters:
- SCHMCircuitID = 0
- UOID = @Value(UOID)   # Uoid
- UGUID = @Value(UGUID)   # Uguid
- STATUS = @Value(STATUS)   # Status
- CIRCUITID = @Value(CIRCUITID)   # Circuitid
- CIRCUITIDS = @Value(CircuitIds)   # Circuitids
- OPERATINGVOLTAGE = @Value(OPERATINGVOLTAGE)   # Operatingvoltage
- FEEDERTYPE = @Value(FEEDERTYPE)   # Feedertype
- CLIENTFEEDERTYPE = @Value(clientFeederType)   # Clientfeedertype
- CLIENTOPERATINGVOLTAGE = @Value(clientOperatingVoltage)   # Clientoperatingvoltage

Input (input)
    -> Tester_3
Tester_3
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> Tester_CircuitID_4
Tester_CircuitID_4
    TEST_MODE = Automatic
    TEST_DESCRIPTION = ""
    BOOL_OP = OR
    TEST_CLAUSE = TEST $(SCHMCircuitID) = 0
    PASSED -> AttributeRenamer_2
    FAILED -> Tester_CircuitID_3
Tester_CircuitID_3
    TEST_MODE = Automatic
    TEST_DESCRIPTION = ""
    COMPOSITE_TEST = 1
    BOOL_OP = COMPOSITE
    TEST_CLAUSE = TEST @Value(CIRCUITID) = $(SCHMCircuitID)
    PASSED -> AttributeRenamer_2
AttributeRenamer_2
    ATTR_LIST = UOID,OBJECTID,"",UGUID,GLOBALID,""
    -> Output (output)
Output (output)

FME custom transformer SetLayerOHUGOpenPoint

Parameters:
- SUBTYPE = @Value(SUBTYPE)   # Subtype

Input (input)
    -> SetLayerNameOHUG_2
SetLayerNameOHUG_2: AttributeCreator
    ATTR_LIST = autocad_layer,"FME_CONDITIONAL:DEFAULT_VALUE'_FME_NO_OP_'BOOL_OP;AND;COMPOSITE_TEST;<Unused>;TEST @Value(SUBTYPE) IN 3,9'MAP-ELEC-EXIST-DOH'FME_NUM_CONDITIONS2___"
    -> Output (output)
Output (output)

FME custom transformer ProcessDeviceGroup_and_Anno

Parameters:
- scale = 500
- output_file_name = schm_to_cad
- FONTNAME = @Value(FONTNAME)   # Fontname
- BOLD = @Value(BOLD)   # Bold
- OBJECTID = @Value(OBJECTID)   # Objectid
- GEODB_TEXT_STRING = @Value(geodb_text_string)   # Geodb Text String
- FME_GEOMETRY = @Value(fme_geometry)   # Fme Geometry
- FEATUREID = @Value(FEATUREID)   # Featureid
- DEVICEGROUPTYPE = @Value(DEVICEGROUPTYPE)   # Devicegrouptype
- ITALIC = @Value(ITALIC)   # Italic
- SCHEMATICTID = @Value(SCHEMATICTID)   # Schematictid
- UOID = @Value(UOID)   # Uoid
- SUBTYPE = @Value(SUBTYPE)   # Subtype
- ROTATION = @Value(ROTATION)   # Rotation
- UGUID = @Value(UGUID)   # Uguid
- STATUS = @Value(STATUS)   # Status
- CIRCUITID = @Value(CIRCUITID)   # Circuitid
- CIRCUITIDS = @Value(CircuitIds)   # Circuitids
- FEEDERTYPE = @Value(FEEDERTYPE)   # Feedertype
- CLIENTFEEDERTYPE = @Value(clientFeederType)   # Clientfeedertype

SetDeviceGroupBlockName1_2: AttributeCreator [off]
    ATTR_LIST = autocad_block_name,"FME_CONDITIONAL:DEFAULT_VALUE'EEDGDEFAULT'BOOL_OP;COMPOSITE;COMPOSITE_TEST;(1 AND 2) OR (1 AND 3) OR (1 AND 4) OR (1 AND 5) OR (1 AND 6) OR (1 AND 7) OR (1 AND 8) OR (1 AND 9) OR (1 AND 10) OR (1 AND 11) OR (1 AND 12) OR (1 AND 13) OR (1 AND 14) OR (1 AND 15) OR (1 AND 16) OR (1 AND 17) OR (1 AND 18) OR (1 AND 19) OR (1 AND 20) OR (1 AND 21) OR (1 AND 22) OR (1 AND 23);TEST @Value(SUBTYPE) = 3;TEST @Value(DEVICEGROUPTYPE) = 1;TEST @Value(DEVICEGROUPTYPE) = 16;TEST @Value(DEVICEGROUPTYPE) = 19;TEST @Value(DEVICEGROUPTYPE) = 2;TEST @Value(DEVICEGROUPTYPE) = 20;TEST @Value(DEVICEGROUPTYPE) = 21;TEST @Value(DEVICEGROUPTYPE) = 22;TEST @Value(DEVICEGROUPTYPE) = 23;TEST @Value(DEVICEGROUPTYPE) = 24;TEST @Value(DEVICEGROUPTYPE) = 25;TEST @Value(DEVICEGROUPTYPE) = 26;TEST @Value(DEVICEGROUPTYPE) = 28;TEST @Value(DEVICEGROUPTYPE) = 29;TEST @Value(DEVICEGROUPTYPE) = 30;TEST @Value(DEVICEGROUPTYPE) = 31;TEST @Value(DEVICEGROUPTYPE) = 32;TEST @Value(DEVICEGROUPTYPE) = 33;TEST @Value(DEVICEGROUPTYPE) = 34;TEST @Value(DEVICEGROUPTYPE) = 35;TEST @Value(DEVICEGROUPTYPE) = 36;TEST @Value(DEVICEGROUPTYPE) = 37;TEST @Value(DEVICEGROUPTYPE) = 17'EEDG162'BOOL_OP;COMPOSITE;COMPOSITE_TEST;(1 AND 3) OR (2 AND 4) OR (2 AND 5) OR (2 AND 6) OR (2 AND 7) OR (2 AND 8) OR (1 AND 9) OR (1 AND 10) OR (1 AND 11);TEST @Value(SUBTYPE) = 3;TEST @Value(SUBTYPE) = 2;TEST @Value(DEVICEGROUPTYPE) = 18;TEST @Value(DEVICEGROUPTYPE) = 20;TEST @Value(DEVICEGROUPTYPE) = 21;TEST @Value(DEVICEGROUPTYPE) = 22;TEST @Value(DEVICEGROUPTYPE) = 23;TEST @Value(DEVICEGROUPTYPE) = 24;TEST @Value(DEVICEGROUPTYPE) = 27;TEST @Value(DEVICEGROUPTYPE) = 3;TEST @Value(DEVICEGROUPTYPE) = 38'EEDG208'BOOL_OP;COMPOSITE;COMPOSITE_TEST;(1 AND 2) OR (1 AND 3);TEST @Value(SUBTYPE) = 3;TEST @Value(DEVICEGROUPTYPE) = 4;TEST @Value(DEVICEGROUPTYPE) = 39'EEDG216'BOOL_OP;COMPOSITE;COMPOSITE_TEST;(1 AND 2) OR (1 AND 3);TEST @Value(SUBTYPE) = 3;TEST @Value(DEVICEGROUPTYPE) = 5;TEST @Value(DEVICEGROUPTYPE) = 40'EEDG218'BOOL_OP;COMPOSITE;COMPOSITE_TEST;(1 AND 3) OR (1 AND 4) OR (2 AND 5);TEST @Value(SUBTYPE) = 3;TEST @Value(SUBTYPE) = 2;TEST @Value(DEVICEGROUPTYPE) = 6;TEST @Value(DEVICEGROUPTYPE) = 41;TEST @Value(DEVICEGROUPTYPE) = 28'EEDG220'BOOL_OP;COMPOSITE;COMPOSITE_TEST;(1 AND 3) OR (1 AND 4) OR (1 AND 5) or (1 AND 6);TEST @Value(SUBTYPE) = 3;TEST @Value(SUBTYPE) = 2;TEST @Value(DEVICEGROUPTYPE) = 7;TEST @Value(DEVICEGROUPTYPE) = 8;TEST @Value(DEVICEGROUPTYPE) = 14;TEST @Value(DEVICEGROUPTYPE) = 42'EEDG222'BOOL_OP;COMPOSITE;COMPOSITE_TEST;(1 AND 3) OR (1 AND 4) OR (2 AND 5);TEST @Value(SUBTYPE) = 3;TEST @Value(SUBTYPE) = 2;TEST @Value(DEVICEGROUPTYPE) = 9;TEST @Value(DEVICEGROUPTYPE) = 15;TEST @Value(DEVICEGROUPTYPE) = 43'EEDG224'BOOL_OP;COMPOSITE;COMPOSITE_TEST;(1 AND 2) OR (1 AND 3);TEST @Value(SUBTYPE) = 3;TEST @Value(DEVICEGROUPTYPE) = 10;TEST @Value(DEVICEGROUPTYPE) = 44'EEDG226'BOOL_OP;COMPOSITE;COMPOSITE_TEST;(1 AND 2) OR (1 AND 3);TEST @Value(SUBTYPE) = 3;TEST @Value(DEVICEGROUPTYPE) = 11;TEST @Value(DEVICEGROUPTYPE) = 45'EEDG228'BOOL_OP;COMPOSITE;COMPOSITE_TEST;(1 AND 2) OR (1 AND 3);TEST @Value(SUBTYPE) = 3;TEST @Value(DEVICEGROUPTYPE) = 12;TEST @Value(DEVICEGROUPTYPE) = 46'EEDG230'BOOL_OP;COMPOSITE;COMPOSITE_TEST;(1 AND 3) OR (1 AND 4) OR (2 AND 5) OR (2 AND 6) OR (2 AND 7);TEST @Value(SUBTYPE) = 3;TEST @Value(SUBTYPE) = 2;TEST @Value(DEVICEGROUPTYPE) = 13;TEST @Value(DEVICEGROUPTYPE) = 47;TEST @Value(DEVICEGROUPTYPE) = 25;TEST @Value(DEVICEGROUPTYPE) = 26;TEST @Value(DEVICEGROUPTYPE) = 27'EEDG232'BOOL_OP;COMPOSITE;COMPOSITE_TEST;(1 AND 2) OR (1 AND 3) OR (1 AND 4);TEST @Value(SUBTYPE) = 2;TEST @Value(DEVICEGROUPTYPE) = 1;TEST @Value(DEVICEGROUPTYPE) = 4;TEST @Value(DEVICEGROUPTYPE) = 9'EEDG69-21_5'BOOL_OP;COMPOSITE;COMPOSITE_TEST;(1 AND 2) OR (1 AND 3);TEST @Value(SUBTYPE) = 2;TEST @Value(DEVICEGROUPTYPE) = 2;TEST @Value(DEVICEGROUPTYPE) = 32'EEDG69_2'BOOL_OP;COMPOSITE;COMPOSITE_TEST;(1 AND 2) OR (1 AND 3) OR (1 AND 4) OR (1 AND 5) OR (1 AND 6) OR (1 AND 7) OR (1 AND 8) OR (1 AND 9) OR (1 AND 10) OR (1 AND 11) OR (1 AND 12) OR (1 AND 13);TEST @Value(SUBTYPE) = 2;TEST @Value(DEVICEGROUPTYPE) = 11;TEST @Value(DEVICEGROUPTYPE) = 16;TEST @Value(DEVICEGROUPTYPE) = 17;TEST @Value(DEVICEGROUPTYPE) = 18;TEST @Value(DEVICEGROUPTYPE) = 19;TEST @Value(DEVICEGROUPTYPE) = 3;TEST @Value(DEVICEGROUPTYPE) = 30;TEST @Value(DEVICEGROUPTYPE) = 31;TEST @Value(DEVICEGROUPTYPE) = 5;TEST @Value(DEVICEGROUPTYPE) = 6;TEST @Value(DEVICEGROUPTYPE) = 8;TEST @Value(DEVICEGROUPTYPE) = 15'EEDG69-30'BOOL_OP;COMPOSITE;COMPOSITE_TEST;(1 AND 2) OR (1 AND 3) OR (1 AND 4) OR (1 AND 5);TEST @Value(SUBTYPE) = 2;TEST @Value(DEVICEGROUPTYPE) = 12;TEST @Value(DEVICEGROUPTYPE) = 13;TEST @Value(DEVICEGROUPTYPE) = 14;TEST @Value(DEVICEGROUPTYPE) = 7'EEDG69-28'BOOL_OP;AND;COMPOSITE_TEST;<Unused>;TEST @Value(SUBTYPE) = 2;TEST @Value(DEVICEGROUPTYPE) = 10'EEDG69-25'BOOL_OP;AND;COMPOSITE_TEST;<Unused>;TEST @Value(SUBTYPE) = 2;TEST @Value(DEVICEGROUPTYPE) = 29'EEDG69-20'BOOL_OP;AND;COMPOSITE_TEST;<Unused>;TEST @Value(STATUS) = 0'EEDGDEFAULTP'FME_NUM_CONDITIONS19___",autocad_layer,"FME_CONDITIONAL:DEFAULT_VALUE'_FME_NO_OP_'BOOL_OP;AND;COMPOSITE_TEST;<Unused>;TEST @Value(SUBTYPE) = 1'MAP-ELEC-EXIST-DOH'BOOL_OP;AND;COMPOSITE_TEST;<Unused>;TEST @Value(SUBTYPE) IN 2,3'MAP-ELEC-EXIST-DUG'FME_NUM_CONDITIONS3___",autocad_entity,autocad_insert,autocad_rotation,@Value(ROTATION),output_file_name,$(output_file_name)
SetDeviceGroupBlockName_Input (input)
    -> SetDeviceGroupBlockName1
SetDeviceGroupBlockName1: AttributeCreator
    ATTR_LIST = autocad_block_name,"FME_CONDITIONAL:DEFAULT_VALUE''BOOL_OP;COMPOSITE;COMPOSITE_TEST;(1 AND 2) OR (1 AND 3) OR (1 AND 4) OR (1 AND 5) OR (1 AND 6) OR (1 AND 7) OR (1 AND 8) OR (1 AND 9) OR (1 AND 10) OR (1 AND 11) OR (1 AND 12) OR (1 AND 13) OR (1 AND 14) OR (1 AND 15) OR (1 AND 16) OR (1 AND 17) OR (1 AND 18) OR (1 AND 19) OR (1 AND 20) OR (1 AND 21) OR (1 AND 22) OR (1 AND 23);TEST @Value(SUBTYPE) = 3;TEST @Value(DEVICEGROUPTYPE) = 1;TEST @Value(DEVICEGROUPTYPE) = 16;TEST @Value(DEVICEGROUPTYPE) = 19;TEST @Value(DEVICEGROUPTYPE) = 2;TEST @Value(DEVICEGROUPTYPE) = 20;TEST @Value(DEVICEGROUPTYPE) = 21;TEST @Value(DEVICEGROUPTYPE) = 22;TEST @Value(DEVICEGROUPTYPE) = 23;TEST @Value(DEVICEGROUPTYPE) = 24;TEST @Value(DEVICEGROUPTYPE) = 25;TEST @Value(DEVICEGROUPTYPE) = 26;TEST @Value(DEVICEGROUPTYPE) = 28;TEST @Value(DEVICEGROUPTYPE) = 29;TEST @Value(DEVICEGROUPTYPE) = 30;TEST @Value(DEVICEGROUPTYPE) = 31;TEST @Value(DEVICEGROUPTYPE) = 32;TEST @Value(DEVICEGROUPTYPE) = 33;TEST @Value(DEVICEGROUPTYPE) = 34;TEST @Value(DEVICEGROUPTYPE) = 35;TEST @Value(DEVICEGROUPTYPE) = 36;TEST @Value(DEVICEGROUPTYPE) = 37;TEST @Value(DEVICEGROUPTYPE) = 17'EEDG162'BOOL_OP;COMPOSITE;COMPOSITE_TEST;(1 AND 3) OR (2 AND 4) OR (2 AND 5) OR (2 AND 6) OR (2 AND 7) OR (2 AND 8) OR (1 AND 9) OR (1 AND 10) OR (1 AND 11);TEST @Value(SUBTYPE) = 3;TEST @Value(SUBTYPE) = 2;TEST @Value(DEVICEGROUPTYPE) = 18;TEST @Value(DEVICEGROUPTYPE) = 20;TEST @Value(DEVICEGROUPTYPE) = 21;TEST @Value(DEVICEGROUPTYPE) = 22;TEST @Value(DEVICEGROUPTYPE) = 23;TEST @Value(DEVICEGROUPTYPE) = 24;TEST @Value(DEVICEGROUPTYPE) = 27;TEST @Value(DEVICEGROUPTYPE) = 3;TEST @Value(DEVICEGROUPTYPE) = 38'EEDG208'BOOL_OP;COMPOSITE;COMPOSITE_TEST;(1 AND 2) OR (1 AND 3);TEST @Value(SUBTYPE) = 3;TEST @Value(DEVICEGROUPTYPE) = 4;TEST @Value(DEVICEGROUPTYPE) = 39'EEDG216'BOOL_OP;COMPOSITE;COMPOSITE_TEST;(1 AND 2) OR (1 AND 3);TEST @Value(SUBTYPE) = 3;TEST @Value(DEVICEGROUPTYPE) = 5;TEST @Value(DEVICEGROUPTYPE) = 40'EEDG218'BOOL_OP;COMPOSITE;COMPOSITE_TEST;(1 AND 3) OR (1 AND 4) OR (2 AND 5);TEST @Value(SUBTYPE) = 3;TEST @Value(SUBTYPE) = 2;TEST @Value(DEVICEGROUPTYPE) = 6;TEST @Value(DEVICEGROUPTYPE) = 41;TEST @Value(DEVICEGROUPTYPE) = 28''BOOL_OP;COMPOSITE;COMPOSITE_TEST;(1 AND 3) OR (1 AND 4) OR (1 AND 5) or (1 AND 6);TEST @Value(SUBTYPE) = 3;TEST @Value(SUBTYPE) = 2;TEST @Value(DEVICEGROUPTYPE) = 7;TEST @Value(DEVICEGROUPTYPE) = 8;TEST @Value(DEVICEGROUPTYPE) = 14;TEST @Value(DEVICEGROUPTYPE) = 42''BOOL_OP;COMPOSITE;COMPOSITE_TEST;(1 AND 3) OR (1 AND 4) OR (2 AND 5);TEST @Value(SUBTYPE) = 3;TEST @Value(SUBTYPE) = 2;TEST @Value(DEVICEGROUPTYPE) = 9;TEST @Value(DEVICEGROUPTYPE) = 15;TEST @Value(DEVICEGROUPTYPE) = 43'EEDG224'BOOL_OP;COMPOSITE;COMPOSITE_TEST;(1 AND 2) OR (1 AND 3);TEST @Value(SUBTYPE) = 3;TEST @Value(DEVICEGROUPTYPE) = 10;TEST @Value(DEVICEGROUPTYPE) = 44'EEDG226'BOOL_OP;COMPOSITE;COMPOSITE_TEST;(1 AND 2) OR (1 AND 3);TEST @Value(SUBTYPE) = 3;TEST @Value(DEVICEGROUPTYPE) = 11;TEST @Value(DEVICEGROUPTYPE) = 45'EEDG228'BOOL_OP;COMPOSITE;COMPOSITE_TEST;(1 AND 2) OR (1 AND 3);TEST @Value(SUBTYPE) = 3;TEST @Value(DEVICEGROUPTYPE) = 12;TEST @Value(DEVICEGROUPTYPE) = 46'EEDG230'BOOL_OP;COMPOSITE;COMPOSITE_TEST;(1 AND 3) OR (1 AND 4) OR (2 AND 5) OR (2 AND 6) OR (2 AND 7);TEST @Value(SUBTYPE) = 3;TEST @Value(SUBTYPE) = 2;TEST @Value(DEVICEGROUPTYPE) = 13;TEST @Value(DEVICEGROUPTYPE) = 47;TEST @Value(DEVICEGROUPTYPE) = 25;TEST @Value(DEVICEGROUPTYPE) = 26;TEST @Value(DEVICEGROUPTYPE) = 27'EEDG232'BOOL_OP;COMPOSITE;COMPOSITE_TEST;(1 AND 2) OR (1 AND 3) OR (1 AND 4);TEST @Value(SUBTYPE) = 2;TEST @Value(DEVICEGROUPTYPE) = 1;TEST @Value(DEVICEGROUPTYPE) = 4;TEST @Value(DEVICEGROUPTYPE) = 9'EEDG69-21_5'BOOL_OP;COMPOSITE;COMPOSITE_TEST;(1 AND 2) OR (1 AND 3);TEST @Value(SUBTYPE) = 2;TEST @Value(DEVICEGROUPTYPE) = 2;TEST @Value(DEVICEGROUPTYPE) = 32'EEDG69_2'BOOL_OP;COMPOSITE;COMPOSITE_TEST;(1 AND 2) OR (1 AND 3) OR (1 AND 4) OR (1 AND 5) OR (1 AND 6) OR (1 AND 7) OR (1 AND 8) OR (1 AND 9) OR (1 AND 10) OR (1 AND 11) OR (1 AND 12) OR (1 AND 13);TEST @Value(SUBTYPE) = 2;TEST @Value(DEVICEGROUPTYPE) = 11;TEST @Value(DEVICEGROUPTYPE) = 16;TEST @Value(DEVICEGROUPTYPE) = 17;TEST @Value(DEVICEGROUPTYPE) = 18;TEST @Value(DEVICEGROUPTYPE) = 19;TEST @Value(DEVICEGROUPTYPE) = 3;TEST @Value(DEVICEGROUPTYPE) = 30;TEST @Value(DEVICEGROUPTYPE) = 31;TEST @Value(DEVICEGROUPTYPE) = 5;TEST @Value(DEVICEGROUPTYPE) = 6;TEST @Value(DEVICEGROUPTYPE) = 8;TEST @Value(DEVICEGROUPTYPE) = 15'EEDG69-30'BOOL_OP;COMPOSITE;COMPOSITE_TEST;(1 AND 2) OR (1 AND 3) OR (1 AND 4) OR (1 AND 5);TEST @Value(SUBTYPE) = 2;TEST @Value(DEVICEGROUPTYPE) = 12;TEST @Value(DEVICEGROUPTYPE) = 13;TEST @Value(DEVICEGROUPTYPE) = 14;TEST @Value(DEVICEGROUPTYPE) = 7'EEDG69-28'BOOL_OP;AND;COMPOSITE_TEST;<Unused>;TEST @Value(SUBTYPE) = 2;TEST @Value(DEVICEGROUPTYPE) = 10'EEDG69-25'BOOL_OP;AND;COMPOSITE_TEST;<Unused>;TEST @Value(SUBTYPE) = 2;TEST @Value(DEVICEGROUPTYPE) = 29'EEDG69-20'BOOL_OP;AND;COMPOSITE_TEST;<Unused>;TEST @Value(STATUS) = 0'EEDGDEFAULTP'FME_NUM_CONDITIONS19___",autocad_layer,"FME_CONDITIONAL:DEFAULT_VALUE'_FME_NO_OP_'BOOL_OP;AND;COMPOSITE_TEST;<Unused>;TEST @Value(SUBTYPE) = 1'MAP-ELEC-EXIST-DOH'BOOL_OP;AND;COMPOSITE_TEST;<Unused>;TEST @Value(SUBTYPE) IN 2,3'MAP-ELEC-EXIST-DUG'FME_NUM_CONDITIONS3___",autocad_entity,autocad_insert,autocad_rotation,@Value(ROTATION),output_file_name,$(output_file_name)
    -> Tester_3
Tester_3
    TEST_MODE = Automatic
    TEST_DESCRIPTION = ""
    COMPOSITE_TEST = "1 AND 2 AND (3 OR 4)"
    BOOL_OP = COMPOSITE
    TEST_CLAUSE:
      TEST @Value(STATUS) != 0
      TEST @Value(CircuitIds) CONTAINS @Value(CIRCUITID)
      TEST @Value(clientFeederType) = @Value(FEEDERTYPE)
      TEST @Value(clientFeederType) = -1
    PASSED -> AttributeRenamer_3
AttributeRenamer_3
    ATTR_LIST = UOID,OBJECTID,"",UGUID,GLOBALID,""
    -> RotateToCAD_21
RotateToCAD_21
    SYMBOLROTATION = @Value(ROTATION)
    RotateToCADTemplate_Output -> SetScale_21
SetScale_21
    scale = $(scale)
    SetScaleFromScaleFactor_Output -> Features (output)
    SetScaleFromScaleFactor_Output -> AttributeRemover
Features (output)
AttributeRemover
    REMOVE_ATTRS = autocad_rotation
    -> FeatureMerger_DG1 [input 2]
AnnotationToMText_DG_AttributeCreator_8_Input (input)
    -> RemoveUnplacedAnno
RemoveUnplacedAnno
    STATUS = @Value(STATUS)
    RemoveUnplaced_Passed -> AnnotationToMText_DCR
AnnotationToMText_DCR
    XSCALE = .54
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> FeatureMerger_DG1 [input 1]
FeatureMerger_DG1
    PROCESS_DUPS = No
    MERGE_TYPE = Attributes Only
    SUPPLIERS_FIRST = No
    JOIN_KEYS = @Value(FEATUREID) @Value(OBJECTID) AUTO
    SUPPLIER_PREFIX_DUMMY = YES
    MERGED -> AttributeCreator
AttributeCreator
    ATTR_LIST = output_file_name,$(output_file_name)
    -> Anno (output)
Anno (output)
AnnotationToMTextNotes [off]
    XSCALE = .72
    fme_geometry = " "
    FONTNAME = RomanT
    YSCALE = .72
    BOLD = @Value(BOLD)
    ITALIC = @Value(ITALIC)
    GEODB_TEXT_STRING = @Value(geodb_text_string)
    SCALE = $(scale)

FME custom transformer SetOutputFileName

Parameters:
- output_file_name = gis_to_cad

SetOutputFileName_Input_1 (input)
    -> SetOutputFileName
SetOutputFileName: AttributeCreator
    ATTR_LIST = output_file_name,$(output_file_name)
    -> SetOutputFileName_Output_1 (output)
SetOutputFileName_Output_1 (output)

FME custom transformer RemoveUnplacedAnno

Parameters:
- STATUS = @Value(STATUS)   # Status

RemoveUnplaced_Input (input)
    -> RemoveUnplaced
RemoveUnplaced: Tester
    TEST_MODE = Automatic
    TEST_DESCRIPTION = ""
    BOOL_OP = OR
    TEST_CLAUSE:
      TEST @Value(STATUS) = 0
      TEST STATUS ATTRIBUTE_VALUE_NULL ""
    PASSED -> RemoveUnplaced_Passed (output)
RemoveUnplaced_Passed (output)

FME custom transformer ProcessFuse_and_Anno

Parameters:
- output_file_name = schm_to_cad
- FONTNAME = @Value(FONTNAME)   # Fontname
- BOLD = @Value(BOLD)   # Bold
- OBJECTID = @Value(OBJECTID)   # Objectid
- FEATUREID = @Value(FEATUREID)   # Featureid
- COMPLEXDEVICEIDC = @Value(COMPLEXDEVICEIDC)   # Complexdeviceidc
- ITALIC = @Value(ITALIC)   # Italic
- ANNOTATIONCLASSID = @Value(ANNOTATIONCLASSID)   # Annotationclassid
- STATUS = @Value(STATUS)   # Status
- scale = 500
- SCHEMATICTID = @Value(SCHEMATICTID)   # Schematictid
- UOID = @Value(UOID)   # Uoid
- SUBTYPE = @Value(SUBTYPE)   # Subtype
- UGUID = @Value(UGUID)   # Uguid
- FME_GEOMETRY = @Value(fme_geometry)   # Fme Geometry
- GEODB_TEXT_STRING = @Value(geodb_text_string)   # Geodb Text String
- SUBTYPECD = @Value(SUBTYPECD)   # Subtypecd
- CIRCUITID = @Value(CIRCUITID)   # Circuitid
- CIRCUITIDS = @Value(CircuitIds)   # Circuitids
- OPERATINGVOLTAGE = @Value(OPERATINGVOLTAGE)   # Operatingvoltage
- FEEDERTYPE = @Value(FEEDERTYPE)   # Feedertype
- CLIENTFEEDERTYPE = @Value(clientFeederType)   # Clientfeedertype
- CLIENTOPERATINGVOLTAGE = @Value(clientOperatingVoltage)   # Clientoperatingvoltage

SetVoltageRegulatorBlockName1_Input (input)
    -> SetFuseBlockName1
SetFuseBlockName1: AttributeCreator
    ATTR_LIST = autocad_block_name,"FME_CONDITIONAL:DEFAULT_VALUE'EEFUDEFAULT'BOOL_OP;OR;COMPOSITE_TEST;<Unused>;TEST @Value(SUBTYPECD) = 1'EECO'BOOL_OP;AND;COMPOSITE_TEST;<Unused>;TEST @Value(SUBTYPECD) = 2;TEST @Value(COMPLEXDEVICEIDC) = N'EEFUUG'BOOL_OP;AND;COMPOSITE_TEST;<Unused>;TEST @Value(SUBTYPECD) = 2;TEST @Value(COMPLEXDEVICEIDC) = Y'EEFUUGCPX'FME_NUM_CONDITIONS4___",output_file_name,$(output_file_name),autocad_entity,autocad_insert,autocad_layer,"FME_CONDITIONAL:DEFAULT_VALUE'_FME_NO_OP_'BOOL_OP;AND;COMPOSITE_TEST;<Unused>;TEST @Value(SUBTYPECD) = 1'MAP-ELEC-EXIST-DOH'BOOL_OP;AND;COMPOSITE_TEST;<Unused>;TEST @Value(SUBTYPECD) = 2'MAP-ELEC-EXIST-DUG'FME_NUM_CONDITIONS3___"
    -> Tester_2
Tester_2
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> AttributeRenamer
AttributeRenamer
    ATTR_LIST = UOID,OBJECTID,"",UGUID,GLOBALID,""
    -> SetScale_21
SetScale_21
    scale = $(scale)
    SetScaleFromScaleFactor_Output -> Features (output)
    SetScaleFromScaleFactor_Output -> FeatureMerger_Fuse [input 2]
Features (output)
AnnotationToMText_VR_AttributeCreator_8_Input (input)
    -> RemoveUnplacedAnno
RemoveUnplacedAnno
    STATUS = @Value(STATUS)
    RemoveUnplaced_Passed -> AnnotationToMText_Fuse_2
AnnotationToMText_Fuse_2
    XSCALE = 0.54
    fme_geometry = @Value(fme_geometry)
    FONTNAME = @Value(FONTNAME)
    YSCALE = 0.54
    BOLD = @Value(BOLD)
    ITALIC = @Value(ITALIC)
    GEODB_TEXT_STRING = @Value(geodb_text_string)
    SCALE = $(scale)
    Tester_Passed -> FeatureMerger_Fuse [input 1]
FeatureMerger_Fuse
    PROCESS_DUPS = No
    MERGE_TYPE = Attributes Only
    SUPPLIERS_FIRST = No
    JOIN_KEYS = @Value(FEATUREID) @Value(OBJECTID) AUTO
    SUPPLIER_PREFIX_DUMMY = YES
    MERGED -> Anno (output)
Anno (output)

FME custom transformer RotateToCAD

Parameters:
- SYMBOLROTATION = @Value(SYMBOLROTATION)   # Symbolrotation

RotateToCADTemplate_Input (input)
    -> SymbolRotationExists
SymbolRotationExists: Tester
    TEST_MODE = Automatic
    TEST_DESCRIPTION = ""
    BOOL_OP = OR
    TEST_CLAUSE:
      TEST SYMBOLROTATION NOT_ATTRIBUTE_IS_MISSING ""
      TEST SYMBOLROTATION NOT_ATTRIBUTE_VALUE_NULL ""
      TEST SYMBOLROTATION NOT_ATTRIBUTE_IS_EMPTY ""
    PASSED -> RotateToCADTemplate
    FAILED -> RotateToCADTemplate_Output (output)
RotateToCADTemplate: ExpressionEvaluator
    VAL_ATTR = autocad_rotation
    EXPRESSION = 360-@Value(SYMBOLROTATION)
    -> RotateToCADTemplate_Output (output)
RotateToCADTemplate_Output (output)

FME custom transformer Process CA Street Names

Parameters:
- FULLNAME = @Value(FULLNAME)   # Fullname
- scale =   # Scale
- OBJECTID = @Value(OBJECTID)   # Objectid
- SHIELDNUM = @Value(SHIELDNUM)   # Shieldnum

Clip_Polygon (input)
    -> Clipper
Clipper [off]
    CREATE_AGGREGATES = Yes
    CLIPPED_ATTR = _clipped
    MERGE_ATTRS = No
    PRESERVE_CLIPPEE_EXTENTS = No
    ATTR_PREFIX = clipper_
    CLIP_TYPE = Multiple Clippers
    BOUNDARY_CASES = Treat as Inside
    INSIDE -> LineJoiner
LineJoiner [off]
    GROUP_BY = FULLNAME
    GROUP_BREAK = no
    PRESERVE = no
    TOPOLOGY = End noded
    LINES_AS_SEGMENTS = No
    CONSIDER_NODE_ELEVATION = no
    BREAK = no
    LINE -> ProcessStreetName
ProcessStreetName: AttributeCreator [off]
    ATTR_LIST = autocad_layer,MAP-LAND-MISC
    -> LabelPointReplacer
LabelPointReplacer [off]
    ALWAYSROTATE = yes
    LABATTR = @Value(FULLNAME)
    HEIGHT = 8
    LabelPoint -> AnnotationToMTextHeadings
AnnotationToMTextHeadings [off]
    XSCALE = .72
    fme_geometry = " "
    FONTNAME = RomanT
    YSCALE = .72
    BOLD = 0
    ITALIC = 0
    GEODB_TEXT_STRING = @Value(FULLNAME)
    SCALE = $(scale)
Input (input)
    -> TestFilter
TestFilter
    TEST_LIST = BOOL_OP,OR,COMPOSITE_TEST,<Unused>,TEST_CLAUSE,"TEST @Value(SHIELDNUM) !=  ",Pass
    DEFAULT_VALUE = <UNFILTERED>
    Pass -> ProcessHighways
ProcessHighways: AttributeCreator
    ATTR_LIST = autocad_linetype,ELEOFWY,autocad_layer,MAP-LAND-MISC,autocad_entity,autocad_line
    -> Output (output)
Output (output)

FME custom transformer AnnotationToMTextNotes

Parameters:
- FONTNAME = RomanT   # Fontname
- BOLD = @Value(BOLD)   # Bold
- GEODB_TEXT_STRING = @Value(geodb_text_string)   # Geodb Text String
- ITALIC = @Value(ITALIC)   # Italic
- fme_geometry =   # Test Parameter
- XSCALE = .72   # X
- YSCALE = .72   # Y
- SCALE = @Value(Scale)   # Scale

AttributeCreator_8_Input (input)
    -> Tester_2
Tester_2
    TEST_MODE = Automatic
    TEST_DESCRIPTION = ""
    BOOL_OP = OR
    TEST_CLAUSE = TEST $(fme_geometry) != fme_undefined
    PASSED -> AttributeCreator_8
Note: Create MText string, including / bold and italic settings / [Update] for 500 scale
AttributeCreator_8
    ATTR_LIST = autocad_text_string,@Value(geodb_text_string),autocad_entity,autocad_text,autocad_text_size,"FME_CONDITIONAL:DEFAULT_VALUE'12.5'BOOL_OP;OR;COMPOSITE_TEST;<Unused>;TEST @Value(Scale) = 100'@Evaluate(($(SCALE)*12.5)/100)'FME_NUM_CONDITIONS2___",autocad_shape_name,NOTES,autocad_width_factor,1
    -> Scaler
Note: Scale text size to adjust to / ArcMap display size
Scaler
    XSCALE = $(XSCALE)
    SCALE_ORIGIN = Center Point
    YSCALE = $(YSCALE)
    TEXT_LOC_ONLY = Location and Size
    ZSCALE = 1
    RASTER_SCALING = Extents
    SCALED -> CharacterCodeExtractor
Note: Remove null characters / created when text was split
CharacterCodeExtractor
    SRC_ATTR = geodb_text_string
    CODE_ATTR = _code
    -> Tester
Tester
    TEST_MODE = Automatic
    TEST_DESCRIPTION = ""
    BOOL_OP = AND
    TEST_CLAUSE:
      TEST @Value(geodb_text_string) != ""
      TEST @Value(_code) < 129
    PASSED -> Tester_Passed (output)
Tester_Passed (output)

FME custom transformer SetScale

Parameters:
- scale = 0

ExpressionEvaluator_Input (input)
    -> AttributeCreator
AttributeCreator
    ATTR_LIST = _scaleFactor,"FME_CONDITIONAL:DEFAULT_VALUE'$(scale)'BOOL_OP;OR;COMPOSITE_TEST;<Unused>;TEST $(scale) = 500'400'FME_NUM_CONDITIONS2___"
    -> SetScaleFromScaleFactor
SetScaleFromScaleFactor: AttributeCreator
    ATTR_LIST = autocad_xscale,@Value(_scaleFactor),autocad_yscale,@Value(_scaleFactor),autocad_zscale,@Value(_scaleFactor)
    -> SetScaleFromScaleFactor_Output (output)
SetScaleFromScaleFactor_Output (output)
Note: old
ExpressionEvaluator
    VAL_ATTR = _scaleFactor
    EXPRESSION = $(scale) * 1.0

FME custom transformer ProcessTransformer_and_Anno

Parameters:
- SYMBOLNUMBER = @Value(SYMBOLNUMBER)   # Symbolnumber
- FONTNAME = @Value(FONTNAME)   # Fontname
- BOLD = @Value(BOLD)   # Bold
- INSTALLATIONTYPE = @Value(INSTALLATIONTYPE)   # Installationtype
- GEODB_TEXT_STRING = @Value(geodb_text_string)   # Geodb Text String
- FME_GEOMETRY = @Value(fme_geometry)   # Fme Geometry
- FEATUREID = @Value(FEATUREID)   # Featureid
- ITALIC = @Value(ITALIC)   # Italic
- ANNOTATIONCLASSID = @Value(ANNOTATIONCLASSID)   # Annotationclassid
- STATUS = @Value(STATUS)   # Status
- scale = 500
- ANGLE = @Value(ANGLE)   # Angle
- TEXTSTRING = @Value(TEXTSTRING)   # Textstring
- YOFFSET = @Value(YOFFSET)   # Yoffset
- UOID = @Value(UOID)   # Uoid
- SUBTYPE = @Value(SUBTYPE)   # Subtype
- UGUID = @Value(UGUID)   # Uguid
- ROTATION = @Value(ROTATION)   # Rotation
- CIRCUITID = @Value(CIRCUITID)   # Circuitid
- CIRCUITIDS = @Value(CircuitIds)   # Circuitids
- FEEDERTYPE = @Value(FEEDERTYPE)   # Feedertype
- OPERATINGVOLTAGE = @Value(OPERATINGVOLTAGE)   # Operatingvoltage
- CLIENTFEEDERTYPE = @Value(clientFeederType)   # Clientfeedertype
- CLIENTOPERATINGVOLTAGE = @Value(clientOperatingVoltage)   # Clientoperatingvoltage

SetTransformerBlockName_Input (input)
    -> Tester_2
Tester_2
    TEST_MODE = Automatic
    TEST_DESCRIPTION = ""
    BOOL_OP = AND
    TEST_CLAUSE = TEST @Value(SUBTYPE) IN 2,3,4,5
    PASSED -> SetTransformerBlockName
SetTransformerBlockName: AttributeCreator
    ATTR_LIST = autocad_block_name,"FME_CONDITIONAL:DEFAULT_VALUE'EETXDEFAULT'BOOL_OP;COMPOSITE;COMPOSITE_TEST;(1 OR 2 or 3) AND 4;TEST @Value(SYMBOLNUMBER) = 36;TEST @Value(SYMBOLNUMBER) = 47;TEST @Value(SYMBOLNUMBER) = 64;TEST @Value(STATUS) != 0'EETXOH'BOOL_OP;AND;COMPOSITE_TEST;<Unused>;TEST @Value(SYMBOLNUMBER) = 37;TEST @Value(STATUS) != 0'EETXOBOH'BOOL_OP;COMPOSITE;COMPOSITE_TEST;(1 OR 2) AND 3;TEST @Value(SYMBOLNUMBER) = 38;TEST @Value(SYMBOLNUMBER) = 66;TEST @Value(STATUS) != 0'EETXCBOH'BOOL_OP;COMPOSITE;COMPOSITE_TEST;(1 OR 2 OR 3 OR 4 OR 5 OR 6) AND 7;TEST @Value(SYMBOLNUMBER) = 39;TEST @Value(SYMBOLNUMBER) = 42;TEST @Value(SYMBOLNUMBER) = 43;TEST @Value(SYMBOLNUMBER) = 48;TEST @Value(SYMBOLNUMBER) = 54;TEST @Value(SYMBOLNUMBER) = 55;TEST @Value(STATUS) != 0'EETXUG'BOOL_OP;COMPOSITE;COMPOSITE_TEST;(1 OR 2 OR 3 OR 4 OR 5) AND 6;TEST @Value(SYMBOLNUMBER) = 40;TEST @Value(SYMBOLNUMBER) = 67;TEST @Value(SYMBOLNUMBER) = 41;TEST @Value(SYMBOLNUMBER) = 44;TEST @Value(SYMBOLNUMBER) = 67;TEST @Value(STATUS) != 0'EETXOBUG'BOOL_OP;AND;COMPOSITE_TEST;<Unused>;TEST @Value(SYMBOLNUMBER) = 45;TEST @Value(STATUS) != 0'EETXSUB1INT'BOOL_OP;AND;COMPOSITE_TEST;<Unused>;TEST @Value(SYMBOLNUMBER) = 46;TEST @Value(STATUS) != 0'EETXSUB1AUTO'BOOL_OP;AND;COMPOSITE_TEST;<Unused>;TEST @Value(SYMBOLNUMBER) = 49;TEST @Value(STATUS) != 0'EETXSUBNTWRKSPOT120208'BOOL_OP;AND;COMPOSITE_TEST;<Unused>;TEST @Value(SYMBOLNUMBER) = 50;TEST @Value(STATUS) != 0'EETXSUBNTWRKSPOT277480'BOOL_OP;AND;COMPOSITE_TEST;<Unused>;TEST @Value(SYMBOLNUMBER) = 51;TEST @Value(STATUS) != 0'EETXSUBNTWRK265460'BOOL_OP;AND;COMPOSITE_TEST;<Unused>;TEST @Value(SYMBOLNUMBER) = 52;TEST @Value(STATUS) != 0'EETXSUBNTWRK120004160'BOOL_OP;AND;COMPOSITE_TEST;<Unused>;TEST @Value(SYMBOLNUMBER) = 53;TEST @Value(STATUS) != 0'EETXSUBNTWRK340004160'BOOL_OP;AND;COMPOSITE_TEST;<Unused>;TEST @Value(SYMBOLNUMBER) = 56;TEST @Value(STATUS) != 0'EETXOHOFF1'BOOL_OP;AND;COMPOSITE_TEST;<Unused>;TEST @Value(SYMBOLNUMBER) = 57;TEST @Value(STATUS) != 0'EETXOBOHOFF1'BOOL_OP;AND;COMPOSITE_TEST;<Unused>;TEST @Value(SYMBOLNUMBER) = 58;TEST @Value(STATUS) != 0'EETXCBOHOFF1'BOOL_OP;AND;COMPOSITE_TEST;<Unused>;TEST @Value(SYMBOLNUMBER) = 59;TEST @Value(STATUS) != 0'EETXOHOFF2'BOOL_OP;AND;COMPOSITE_TEST;<Unused>;TEST @Value(SYMBOLNUMBER) = 60;TEST @Value(STATUS) != 0'EETXOBOHOFF2'BOOL_OP;AND;COMPOSITE_TEST;<Unused>;TEST @Value(SYMBOLNUMBER) = 61;TEST @Value(STATUS) != 0'EETXCBOHOFF2'BOOL_OP;COMPOSITE;COMPOSITE_TEST;(1 OR 2) AND 3;TEST @Value(SYMBOLNUMBER) = 62;TEST @Value(SYMBOLNUMBER) = 65;TEST @Value(STATUS) != 0'EETXUGOFF1'BOOL_OP;AND;COMPOSITE_TEST;<Unused>;TEST @Value(SYMBOLNUMBER) = 63;TEST @Value(STATUS) != 0'EETXUGOFF2'BOOL_OP;COMPOSITE;COMPOSITE_TEST;(1 OR 2 OR 3 OR 4 ) AND 5;TEST @Value(SUBTYPE) = 1;TEST @Value(SUBTYPE) = 4;TEST @Value(SUBTYPE) = 7;TEST @Value(SUBTYPE) = 8;TEST @Value(STATUS) = 0'PETXOH'BOOL_OP;COMPOSITE;COMPOSITE_TEST;(1 OR 2 OR 3 OR 4 ) AND 5;TEST @Value(SUBTYPE) = 2;TEST @Value(SUBTYPE) = 3;TEST @Value(SUBTYPE) = 5;TEST @Value(SUBTYPE) = 6;TEST @Value(STATUS) = 0'PETXUG'BOOL_OP;OR;COMPOSITE_TEST;<Unused>;TEST @Value(STATUS) = 0'PETXDEFAULT'FME_NUM_CONDITIONS24___"
    -> Tester_4
Tester_4
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> SetLayerNameTransformersOHUG
SetLayerNameTransformersOHUG: AttributeCreator
    ATTR_LIST = autocad_layer,MAP-ELEC-EXIST-DUG
    -> AttributeRenamer
AttributeRenamer
    ATTR_LIST = UOID,OBJECTID,"",UGUID,GLOBALID,""
    -> SetScale_21
SetScale_21
    scale = $(scale)
    SetScaleFromScaleFactor_Output -> Features (output)
    SetScaleFromScaleFactor_Output -> AttributeRemover
Features (output)
AttributeRemover
    REMOVE_ATTRS = INSTALLATIONTYPE
    -> FeatureMerger_xfmr [input 2]
AnnotationToMText_4_AttributeCreator_8_Input (input)
    -> RemoveUnplacedAnno
RemoveUnplacedAnno
    STATUS = @Value(STATUS)
    RemoveUnplaced_Passed -> AnnotationToMText_Xfmr
Note: old
AnnotationToMText_Xfmr
    XSCALE = 1
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> FeatureMerger_xfmr [input 1]
FeatureMerger_xfmr
    PROCESS_DUPS = No
    MERGE_TYPE = Attributes Only
    SUPPLIERS_FIRST = No
    JOIN_KEYS = @Value(FEATUREID) @Value(OBJECTID) AUTO
    SUPPLIER_PREFIX_DUMMY = YES
    MERGED -> SetScale_2
SetScale_2
    scale = $(scale)
    SetScaleFromScaleFactor_Output -> Anno (output)
Anno (output)

FME custom transformer AnnotationToMTextHeadings

Parameters:
- FONTNAME = RomanT   # Fontname
- BOLD = @Value(BOLD)   # Bold
- GEODB_TEXT_STRING = @Value(geodb_text_string)   # Geodb Text String
- ITALIC = @Value(ITALIC)   # Italic
- fme_geometry =   # Test Parameter
- XSCALE = .72   # X
- YSCALE = .72   # Y
- SCALE = @Value(Scale)   # Scale

AttributeCreator_8_Input (input)
    -> Tester_2
Tester_2
    TEST_MODE = Automatic
    TEST_DESCRIPTION = ""
    BOOL_OP = OR
    TEST_CLAUSE = TEST $(fme_geometry) != fme_undefined
    PASSED -> AttributeCreator_8
Note: Create MText string, including / bold and italic settings
AttributeCreator_8
    ATTR_LIST = autocad_text_string,@Value(geodb_text_string),autocad_entity,autocad_text,autocad_text_size,"FME_CONDITIONAL:DEFAULT_VALUE'15'BOOL_OP;OR;COMPOSITE_TEST;<Unused>;TEST @Value(Scale) <= 100'@Evaluate(($(SCALE)*15)/100)'FME_NUM_CONDITIONS2___",autocad_shape_name,HEADINGS,autocad_width_factor,1
    -> Scaler
Note: Scale text size to adjust to / ArcMap display size
Scaler
    XSCALE = $(XSCALE)
    SCALE_ORIGIN = Center Point
    YSCALE = $(YSCALE)
    TEXT_LOC_ONLY = Location and Size
    ZSCALE = 1
    RASTER_SCALING = Extents
    SCALED -> CharacterCodeExtractor
Note: Remove null characters / created when text was split
CharacterCodeExtractor
    SRC_ATTR = geodb_text_string
    CODE_ATTR = _code
    -> Tester
Tester
    TEST_MODE = Automatic
    TEST_DESCRIPTION = ""
    BOOL_OP = AND
    TEST_CLAUSE:
      TEST @Value(geodb_text_string) != ""
      TEST @Value(_code) < 129
    PASSED -> Tester_Passed (output)
Tester_Passed (output)

FME custom transformer SetLayerOHUG

Parameters:
- INSTALLATIONTYPE = @Value(INSTALLATIONTYPE)   # Installationtype
- STATUS = @Value(STATUS)   # Status

Input (input)
    -> SetLayerNameOHUG_4
SetLayerNameOHUG_4: AttributeCreator
    ATTR_LIST = autocad_layer,"FME_CONDITIONAL:DEFAULT_VALUE'_FME_NO_OP_'BOOL_OP;AND;COMPOSITE_TEST;<Unused>;TEST @Value(INSTALLATIONTYPE) = OH;TEST @Value(STATUS) != 0'MAP-ELEC-EXIST-DOH'BOOL_OP;AND;COMPOSITE_TEST;<Unused>;TEST @Value(INSTALLATIONTYPE) != OH;TEST @Value(STATUS) != 0'MAP-ELEC-EXIST-DUG'FME_NUM_CONDITIONS3___"
    -> Output (output)
Output (output)

FME custom transformer ProcessTie

Parameters:
- output_file_name = unit_test_dwg
- SCHMCircuitID = 0
- STATUS = @Value(STATUS)   # Status
- CIRCUITID = @Value(CIRCUITID)   # Circuitid
- UOID = @Value(UOID)   # Uoid
- UGUID = @Value(UGUID)   # Uguid
- OUTPUT_FILE_NAME = @Value(output_file_name)   # Output File Name
- CIRCUITIDS = @Value(CircuitIds)   # Circuitids
- FEEDERTYPE = @Value(FEEDERTYPE)   # Feedertype
- CLIENTFEEDERTYPE = @Value(clientFeederType)   # Clientfeedertype

Input (input)
    -> Tester_2
Tester_2
    TEST_MODE = Automatic
    TEST_DESCRIPTION = ""
    COMPOSITE_TEST = "1 AND 2 AND (3 OR 4)"
    BOOL_OP = COMPOSITE
    TEST_CLAUSE:
      TEST @Value(STATUS) != 0
      TEST @Value(CircuitIds) CONTAINS @Value(CIRCUITID)
      TEST @Value(clientFeederType) = @Value(FEEDERTYPE)
      TEST @Value(clientFeederType) = -1
    PASSED -> Tester_CircuitID_2
Tester_CircuitID_2
    TEST_MODE = Automatic
    TEST_DESCRIPTION = ""
    BOOL_OP = OR
    TEST_CLAUSE = TEST $(SCHMCircuitID) = 0
    FAILED -> Tester_CircuitID
    PASSED -> AttributeRenamer
Tester_CircuitID
    TEST_MODE = Automatic
    TEST_DESCRIPTION = ""
    COMPOSITE_TEST = 1
    BOOL_OP = COMPOSITE
    TEST_CLAUSE = TEST @Value(CIRCUITID) = $(SCHMCircuitID)
    PASSED -> AttributeRenamer
AttributeRenamer
    ATTR_LIST = UOID,OBJECTID,"",UGUID,GLOBALID,""
    -> Output (output)
Output (output)

FME custom transformer ProcessStepDown_and_Anno

Parameters:
- output_file_name = schm_to_cad
- FONTNAME = @Value(FONTNAME)   # Fontname
- BOLD = @Value(BOLD)   # Bold
- OBJECTID = @Value(OBJECTID)   # Objectid
- INSTALLATIONTYPE = @Value(INSTALLATIONTYPE)   # Installationtype
- GEODB_TEXT_STRING = @Value(geodb_text_string)   # Geodb Text String
- FME_GEOMETRY = @Value(fme_geometry)   # Fme Geometry
- FEATUREID = @Value(FEATUREID)   # Featureid
- ITALIC = @Value(ITALIC)   # Italic
- ANNOTATIONCLASSID = @Value(ANNOTATIONCLASSID)   # Annotationclassid
- STATUS = @Value(STATUS)   # Status
- scale = 500
- UOID = @Value(UOID)   # Uoid
- SUBTYPE = @Value(SUBTYPE)   # Subtype
- UGUID = @Value(UGUID)   # Uguid
- CIRCUITID = @Value(CIRCUITID)   # Circuitid
- CIRCUITIDS = @Value(CircuitIds)   # Circuitids
- OPERATINGVOLTAGE = @Value(OPERATINGVOLTAGE)   # Operatingvoltage
- FEEDERTYPE = @Value(FEEDERTYPE)   # Feedertype
- CLIENTFEEDERTYPE = @Value(clientFeederType)   # Clientfeedertype
- CLIENTOPERATINGVOLTAGE = @Value(clientOperatingVoltage)   # Clientoperatingvoltage

SetStepDownBlockName_Input (input)
    -> SetStepDownBlockName1
SetStepDownBlockName1: AttributeCreator
    ATTR_LIST = autocad_block_name,"FME_CONDITIONAL:DEFAULT_VALUE'EETXDEFAULT'BOOL_OP;AND;COMPOSITE_TEST;<Unused>;TEST @Value(INSTALLATIONTYPE) = OH;TEST @Value(STATUS) != 0'EETXOH'BOOL_OP;COMPOSITE;COMPOSITE_TEST;(1 OR 2 OR 3) AND 4;TEST @Value(INSTALLATIONTYPE) = SUB;TEST @Value(INSTALLATIONTYPE) = UG;TEST @Value(INSTALLATIONTYPE) = PAD;TEST @Value(STATUS) != 0'EETXUG'BOOL_OP;OR;COMPOSITE_TEST;<Unused>;TEST @Value(STATUS) = 0'PESD'FME_NUM_CONDITIONS4___",autocad_layer,"FME_CONDITIONAL:DEFAULT_VALUE''BOOL_OP;AND;COMPOSITE_TEST;<Unused>;TEST @Value(INSTALLATIONTYPE) = OH;TEST @Value(STATUS) != 0'MAP-ELEC-EXIST-DOH'BOOL_OP;AND;COMPOSITE_TEST;<Unused>;TEST @Value(INSTALLATIONTYPE) != OH;TEST @Value(STATUS) != 0'MAP-ELEC-EXIST-DUG'FME_NUM_CONDITIONS3___",output_file_name,$(output_file_name),autocad_entity,autocad_insert
    -> Tester_2
Tester_2
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> AttributeRenamer
AttributeRenamer
    ATTR_LIST = UOID,OBJECTID,"",UGUID,GLOBALID,""
    -> SetScale_21
SetScale_21
    scale = $(scale)
    SetScaleFromScaleFactor_Output -> Features (output)
    SetScaleFromScaleFactor_Output -> FeatureMerger_StepDown1 [input 2]
Features (output)
AnnotationToMText_SD_AttributeCreator_8_Input (input)
    -> RemoveUnplacedAnno
RemoveUnplacedAnno
    STATUS = @Value(STATUS)
    RemoveUnplaced_Passed -> AnnotationToMText_SD1
AnnotationToMText_SD1
    XSCALE = .54
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> FeatureMerger_StepDown1 [input 1]
FeatureMerger_StepDown1
    PROCESS_DUPS = No
    MERGE_TYPE = Attributes Only
    SUPPLIERS_FIRST = No
    JOIN_KEYS = @Value(FEATUREID) @Value(OBJECTID) AUTO
    SUPPLIER_PREFIX_DUMMY = YES
    MERGED -> Anno (output)
Anno (output)

FME custom transformer ProcessServiceLocation

Parameters:
- output_file_name = mallesham
- scale = 500
- UOID = @Value(UOID)   # Uoid
- UGUID = @Value(UGUID)   # Uguid
- CLIENTFEEDERTYPE = @Value(clientFeederType)   # Clientfeedertype
- FEEDERTYPE = @Value(FEEDERTYPE)   # Feedertype
- STATUS = @Value(STATUS)   # Status
- CIRCUITID = @Value(CIRCUITID)   # Circuitid
- GENCATEGORY = @Value(GENCATEGORY)   # Gencategory
- CIRCUITIDS = @Value(CircuitIds)   # Circuitids

SetServiceLocationBlockName_Input (input)
    -> SetServiceLocationBlockName
    -> SetServiceLocationBlockName_2 [off]
SetServiceLocationBlockName: AttributeCreator
    ATTR_LIST = autocad_block_name,"FME_CONDITIONAL:DEFAULT_VALUE'_FME_NO_OP_'BOOL_OP;AND;COMPOSITE_TEST;<Unused>;TEST @Value(STATUS) > 0;TEST @Value(GENCATEGORY) = 1'EEGEN'BOOL_OP;AND;COMPOSITE_TEST;<Unused>;TEST @Value(STATUS) > 0;TEST @Value(GENCATEGORY) = 2'EESGSL'BOOL_OP;COMPOSITE;COMPOSITE_TEST;(1 AND 2) OR (1 AND 3);TEST @Value(STATUS) > 0;TEST @Value(GENCATEGORY) = 0;TEST GENCATEGORY ATTRIBUTE_VALUE_NULL _FME_BLANK_STRING_'EESERL'FME_NUM_CONDITIONS4___",autocad_layer,"FME_CONDITIONAL:DEFAULT_VALUE'_FME_NO_OP_'BOOL_OP;OR;COMPOSITE_TEST;<Unused>;TEST @Value(STATUS) != 0'MAP-ELEC-UGSERVICE'FME_NUM_CONDITIONS2___",output_file_name,$(output_file_name),autocad_entity,autocad_insert,autocad_color,"FME_CONDITIONAL:DEFAULT_VALUE'_FME_NO_OP_'BOOL_OP;OR;COMPOSITE_TEST;<Unused>;TEST @Value(STATUS) > 0'0'FME_NUM_CONDITIONS2___"
    -> Tester_3
Tester_3
    TEST_MODE = Automatic
    TEST_DESCRIPTION = ""
    COMPOSITE_TEST = "1 AND 2 AND (3 OR 4)"
    BOOL_OP = COMPOSITE
    TEST_CLAUSE:
      TEST @Value(STATUS) != 0
      TEST @Value(CircuitIds) CONTAINS @Value(CIRCUITID)
      TEST @Value(clientFeederType) = @Value(FEEDERTYPE)
      TEST @Value(clientFeederType) = -1
    PASSED -> AttributeRenamer
SetServiceLocationBlockName_2: AttributeCreator [off]
    ATTR_LIST = autocad_block_name,EESERL,autocad_layer,MAP-ELEC-UGSERVICE,output_file_name,$(output_file_name),autocad_entity,autocad_insert,autocad_color,0
    -> AttributeRenamer [off]
AttributeRenamer
    ATTR_LIST = UOID,OBJECTID,"",UGUID,GLOBALID,""
    -> SetScale_21
SetScale_21
    scale = $(scale)
    SetScaleFromScaleFactor_Output -> Feature (output)
Feature (output)

FME custom transformer AnnotationToMText

Parameters:
- FONTNAME = @Value(FONTNAME)   # Fontname
- BOLD = @Value(BOLD)   # Bold
- GEODB_TEXT_STRING = @Value(geodb_text_string)   # Geodb Text String
- ITALIC = @Value(ITALIC)   # Italic
- fme_geometry =   # Test Parameter
- SCALE = @Value(Scale)   # Scale
- XSCALE = 1   # X
- YSCALE = 1   # Y

AttributeCreator_8_Input (input)
    -> Tester_2
Tester_2
    TEST_MODE = Automatic
    TEST_DESCRIPTION = ""
    BOOL_OP = OR
    TEST_CLAUSE = TEST $(fme_geometry) != fme_undefined
    PASSED -> AttributeCreator_3
Note: Create MText string, including / bold and italic settings / [Updated] address 500 scale
AttributeCreator_3
    ATTR_LIST = autocad_entity,autocad_text,autocad_shape_name,LABELS,autocad_text_size,"FME_CONDITIONAL:DEFAULT_VALUE'11'BOOL_OP;OR;COMPOSITE_TEST;<Unused>;TEST @Value(Scale) = 250'11'BOOL_OP;OR;COMPOSITE_TEST;<Unused>;TEST @Value(Scale) = 500'11'FME_NUM_CONDITIONS3___",autocad_text_string,@Value(geodb_text_string),autocad_width_factor,0.6
    -> Scaler
Note: Scale text size to adjust to / ArcMap display size
Scaler
    XSCALE = $(XSCALE)
    SCALE_ORIGIN = Center Point
    YSCALE = $(YSCALE)
    TEXT_LOC_ONLY = Location Only
    ZSCALE = 1
    RASTER_SCALING = Extents
    SCALED -> CharacterCodeExtractor
Note: Remove null characters / created when text was split
CharacterCodeExtractor
    SRC_ATTR = geodb_text_string
    CODE_ATTR = _code
    -> Tester
Tester
    TEST_MODE = Automatic
    TEST_DESCRIPTION = ""
    BOOL_OP = AND
    TEST_CLAUSE:
      TEST @Value(geodb_text_string) != ""
      TEST @Value(_code) < 129
    PASSED -> Tester_Passed (output)
Tester_Passed (output)

FME custom transformer ProcessPrimaryGeneration_and_Anno

Parameters:
- output_file_name = schm_to_cad
- STATUS = @Value(STATUS)   # Status
- scale = 500
- SCHEMATICTID = @Value(SCHEMATICTID)   # Schematictid
- UOID = @Value(UOID)   # Uoid
- UGUID = @Value(UGUID)   # Uguid
- SUBTYPE = @Value(SUBTYPE)   # Subtype
- FONTNAME = @Value(FONTNAME)   # Fontname
- BOLD = @Value(BOLD)   # Bold
- OBJECTID = @Value(OBJECTID)   # Objectid
- GEODB_TEXT_STRING = @Value(geodb_text_string)   # Geodb Text String
- FME_GEOMETRY = @Value(fme_geometry)   # Fme Geometry
- FEATUREID = @Value(FEATUREID)   # Featureid
- ITALIC = @Value(ITALIC)   # Italic
- ANNOTATIONCLASSID = @Value(ANNOTATIONCLASSID)   # Annotationclassid
- CIRCUITID = @Value(CIRCUITID)   # Circuitid
- CIRCUITIDS = @Value(CircuitIds)   # Circuitids
- FEEDERTYPE = @Value(FEEDERTYPE)   # Feedertype
- CLIENTFEEDERTYPE = @Value(clientFeederType)   # Clientfeedertype

SetPrimaryGenerationBlockName_Input (input)
    -> SetPrimaryGenerationBlockName1
SetPrimaryGenerationBlockName1: AttributeCreator
    ATTR_LIST = autocad_block_name,"FME_CONDITIONAL:DEFAULT_VALUE'EEPGDEFAULT'BOOL_OP;AND;COMPOSITE_TEST;<Unused>;TEST @Value(SUBTYPE) = 1;TEST @Value(STATUS) != 0'EEBGEN'BOOL_OP;AND;COMPOSITE_TEST;<Unused>;TEST @Value(SUBTYPE) = 1;TEST @Value(STATUS) = 0'PEBGEN'BOOL_OP;AND;COMPOSITE_TEST;<Unused>;TEST @Value(SUBTYPE) = 2;TEST @Value(STATUS) != 0'EEGEN'BOOL_OP;AND;COMPOSITE_TEST;<Unused>;TEST @Value(SUBTYPE) = 2;TEST @Value(STATUS) = 0'PEGEN'BOOL_OP;AND;COMPOSITE_TEST;<Unused>;TEST @Value(SUBTYPE) = 3;TEST @Value(STATUS) != 0'EECGEN'BOOL_OP;AND;COMPOSITE_TEST;<Unused>;TEST @Value(SUBTYPE) = 3;TEST @Value(STATUS) = 0'PECGEN'BOOL_OP;AND;COMPOSITE_TEST;<Unused>;TEST @Value(STATUS) = 0'PEPGEN'FME_NUM_CONDITIONS8___",autocad_layer,"FME_CONDITIONAL:DEFAULT_VALUE'_FME_NO_OP_'BOOL_OP;OR;COMPOSITE_TEST;<Unused>;TEST @Value(STATUS) != 0'MAP-ELEC-EXIST-DOH'FME_NUM_CONDITIONS2___",output_file_name,$(output_file_name),autocad_entity,autocad_insert
    -> Tester_3
Tester_3
    TEST_MODE = Automatic
    TEST_DESCRIPTION = ""
    COMPOSITE_TEST = "1 AND 2 AND (3 OR 4)"
    BOOL_OP = COMPOSITE
    TEST_CLAUSE:
      TEST @Value(STATUS) != 0
      TEST @Value(CircuitIds) CONTAINS @Value(CIRCUITID)
      TEST @Value(clientFeederType) = @Value(FEEDERTYPE)
      TEST @Value(clientFeederType) = -1
    PASSED -> AttributeRenamer
AttributeRenamer
    ATTR_LIST = UOID,OBJECTID,"",UGUID,GLOBALID,""
    -> SetScale_21
SetScale_21
    scale = $(scale)
    SetScaleFromScaleFactor_Output -> Features (output)
    SetScaleFromScaleFactor_Output -> FeatureMerger_SecondaryDCR [input 2]
Features (output)
AnnotationToMText_84_AttributeCreator_8_Input_2 (input)
    -> RemoveUnplacedAnno
RemoveUnplacedAnno
    STATUS = @Value(STATUS)
    RemoveUnplaced_Passed -> AnnotationToMText_DCR
AnnotationToMText_DCR
    XSCALE = .54
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> FeatureMerger_SecondaryDCR [input 1]
FeatureMerger_SecondaryDCR
    PROCESS_DUPS = No
    MERGE_TYPE = Attributes Only
    SUPPLIERS_FIRST = No
    JOIN_KEYS = @Value(FEATUREID) @Value(OBJECTID) AUTO
    SUPPLIER_PREFIX_DUMMY = YES
    MERGED -> Anno (output)
Anno (output)

FME custom transformer ProcessSwitches_and_Anno

Parameters:
- SYMBOLNUMBER = @Value(SYMBOLNUMBER)   # Symbolnumber
- FONTNAME = @Value(FONTNAME)   # Fontname
- BOLD = @Value(BOLD)   # Bold
- FEATUREID = @Value(FEATUREID)   # Featureid
- GEODB_TEXT_STRING = @Value(geodb_text_string)   # Geodb Text String
- FME_GEOMETRY = @Value(fme_geometry)   # Fme Geometry
- ITALIC = @Value(ITALIC)   # Italic
- ANNOTATIONCLASSID = @Value(ANNOTATIONCLASSID)   # Annotationclassid
- TEXTSTRING = @Value(TEXTSTRING)   # Textstring
- STATUS = @Value(STATUS)   # Status
- scale = 500
- UOID = @Value(UOID)   # Uoid
- UGUID = @Value(UGUID)   # Uguid
- CIRCUITID = @Value(CIRCUITID)   # Circuitid
- SUBTYPE = @Value(SUBTYPE)   # Subtype
- SCHEMATICTID = @Value(SCHEMATICTID)   # Schematictid
- SCHMCircuitID = 0
- CIRCUITIDS = @Value(CircuitIds)   # Circuitids
- FEEDERTYPE = @Value(FEEDERTYPE)   # Feedertype
- OPERATINGVOLTAGE = @Value(OPERATINGVOLTAGE)   # Operatingvoltage
- CLIENTFEEDERTYPE = @Value(clientFeederType)   # Clientfeedertype
- CLIENTOPERATINGVOLTAGE = @Value(clientOperatingVoltage)   # Clientoperatingvoltage

BlockNameSetSwitch_Input (input)
    -> Tester_2
Tester_2
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> BlockNameSetSwitch
BlockNameSetSwitch: AttributeCreator
    ATTR_LIST = autocad_block_name,"FME_CONDITIONAL:DEFAULT_VALUE'EESWDEFAULT'BOOL_OP;OR;COMPOSITE_TEST;<Unused>;TEST @Value(SYMBOLNUMBER) = 18'EEDISC'BOOL_OP;OR;COMPOSITE_TEST;<Unused>;TEST @Value(SYMBOLNUMBER) = 20'EEDISCOH'BOOL_OP;OR;COMPOSITE_TEST;<Unused>;TEST @Value(SYMBOLNUMBER) = 22'EESW'BOOL_OP;OR;COMPOSITE_TEST;<Unused>;TEST @Value(SYMBOLNUMBER) = 23'EESWSUP'BOOL_OP;OR;COMPOSITE_TEST;<Unused>;TEST @Value(SYMBOLNUMBER) = 24'EESWHB'BOOL_OP;OR;COMPOSITE_TEST;<Unused>;TEST @Value(SYMBOLNUMBER) = 25'EESWSB'BOOL_OP;OR;COMPOSITE_TEST;<Unused>;TEST @Value(SYMBOLNUMBER) = 26'EESWAH'BOOL_OP;OR;COMPOSITE_TEST;<Unused>;TEST @Value(SYMBOLNUMBER) = 27'EESWQB'BOOL_OP;OR;COMPOSITE_TEST;<Unused>;TEST @Value(SYMBOLNUMBER) = 28'EESWDISCUG'BOOL_OP;OR;COMPOSITE_TEST;<Unused>;TEST @Value(SYMBOLNUMBER) = 29'EEDISCUGCPX'BOOL_OP;OR;COMPOSITE_TEST;<Unused>;TEST @Value(SYMBOLNUMBER) = 30'EECSW'BOOL_OP;OR;COMPOSITE_TEST;<Unused>;TEST @Value(SYMBOLNUMBER) = 31'EESWUGCPX'BOOL_OP;OR;COMPOSITE_TEST;<Unused>;TEST @Value(SYMBOLNUMBER) = 33'EESCMSUP'BOOL_OP;OR;COMPOSITE_TEST;<Unused>;TEST @Value(SYMBOLNUMBER) = 100'EESWSUPUGCPX'BOOL_OP;OR;COMPOSITE_TEST;<Unused>;TEST @Value(SYMBOLNUMBER) = 99'EESWSUPUG'BOOL_OP;OR;COMPOSITE_TEST;<Unused>;TEST @Value(SYMBOLNUMBER) = 38'EEGRNDSW'BOOL_OP;OR;COMPOSITE_TEST;<Unused>;TEST @Value(SYMBOLNUMBER) = 40'EESCMSOCO'BOOL_OP;OR;COMPOSITE_TEST;<Unused>;TEST @Value(SYMBOLNUMBER) = 41'EESCMSOCOFL'BOOL_OP;OR;COMPOSITE_TEST;<Unused>;TEST @Value(SYMBOLNUMBER) = 42'EESCMSOCI'BOOL_OP;OR;COMPOSITE_TEST;<Unused>;TEST @Value(SYMBOLNUMBER) = 43'EESCMSOCIFL'FME_NUM_CONDITIONS21___",autocad_entity,autocad_insert
    -> AttributeRenamer
AttributeRenamer
    ATTR_LIST = UOID,OBJECTID,"",UGUID,GLOBALID,""
    -> SetSwitchLayerOHUGBasedonSymbolNumber
SetSwitchLayerOHUGBasedonSymbolNumber
    SUBTYPE = @Value(SUBTYPE)
    -> SetScale_21
SetScale_21
    scale = $(scale)
    SetScaleFromScaleFactor_Output -> Features (output)
    SetScaleFromScaleFactor_Output -> FeatureMerger [input 2]
Features (output)
AnnotationToMText_2_AttributeCreator_8_Input (input)
    -> RemoveUnplacedAnno
RemoveUnplacedAnno
    STATUS = @Value(STATUS)
    RemoveUnplaced_Passed -> AnnotationToMText_4
AnnotationToMText_4
    XSCALE = .54
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> FeatureMerger [input 1]
FeatureMerger
    PROCESS_DUPS = No
    MERGE_TYPE = Attributes Only
    SUPPLIERS_FIRST = No
    JOIN_KEYS = @Value(FEATUREID) @Value(OBJECTID) AUTO
    SUPPLIER_PREFIX_DUMMY = YES
    MERGED -> Anno (output)
Anno (output)

FME custom transformer LabelAdderAndOffsetter
To add Label based from a field.
Lables added wil have spaces replaced by return/newline.

Parameters:
- scale = 100
- LABELTEXT = @Value(labeltext)   # Labeltext
- FME_GEOMETRY = @Value(fme_geometry)   # Fme Geometry

Input (input)
    -> AttributeSplitter
AttributeSplitter
    LIST_NAME = _list
    ATTR_NAME = labeltext
    DELIMITER = " "
    TRIM_OPTION = Both
    DROP_EMPTY_PARTS = No
    -> ListConcatenator
ListConcatenator
    VAL_ATTR = _concatenated
    SEP = "\n"
    LIST_ATTR = _list{}
    DROP_EMPTY_PARTS = No
    -> LabelPointReplacer
LabelPointReplacer
    ALWAYSROTATE = no
    LABATTR = @Value(_concatenated)
    HEIGHT = 8
    LabelPoint -> Offsetter
Offsetter
    YOFF = 0
    ZOFF = 0
    XOFF = 7
    OFFSET -> LabelToMText
LabelToMText
    XSCALE = .72
    fme_geometry = @Value(fme_geometry)
    TEXT = @Value(_concatenated)
    FONTSIZE = 8
    YSCALE = .72
    FONTNAME_2 = Arial
    BOLD_2 = 1
    ITALIC_2 = 1
    Tester_Passed -> AnnotationToMText
AnnotationToMText
    XSCALE = .54
    fme_geometry = " "
    FONTNAME = ramonT
    YSCALE = .54
    BOLD = 0
    ITALIC = 0
    GEODB_TEXT_STRING = @Value(_concatenated)
    SCALE = $(scale)
    Tester_Passed -> Output (output)
Output (output)

FME custom transformer ProcessElectricStitchPoint_and_Label

Parameters:
- output_file_name = schm_to_cad
- SUBTYPECD = @Value(SUBTYPECD)   # Subtypecd
- CIRCUITID = @Value(CIRCUITID)   # Circuitid
- scale = 500
- STATUS = @Value(STATUS)   # Status
- ROTATION = @Value(ROTATION)   # Rotation
- UOID = @Value(UOID)   # Uoid
- UGUID = @Value(UGUID)   # Uguid
- FONTNAME = @Value(FONTNAME)   # Fontname
- OBJECTID = @Value(OBJECTID)   # Objectid
- BOLD = @Value(BOLD)   # Bold
- FEATUREID = @Value(FEATUREID)   # Featureid
- GEODB_TEXT_STRING = @Value(geodb_text_string)   # Geodb Text String
- FME_GEOMETRY = @Value(fme_geometry)   # Fme Geometry
- ITALIC = @Value(ITALIC)   # Italic
- ANNOTATIONCLASSID = @Value(ANNOTATIONCLASSID)   # Annotationclassid
- TEXTSTRING = @Value(TEXTSTRING)   # Textstring
- SUBTYPE = @Value(SUBTYPE)   # Subtype
- SCHEMATICTID = @Value(SCHEMATICTID)   # Schematictid
- CIRCUITIDS = @Value(CircuitIds)   # Circuitids
- FEEDERTYPE = @Value(FEEDERTYPE)   # Feedertype
- CLIENTFEEDERTYPE = @Value(clientFeederType)   # Clientfeedertype

SetElectricStitchPointBlockName_2_Input (input)
    -> Tester_2
Tester_2
    TEST_MODE = Automatic
    TEST_DESCRIPTION = ""
    COMPOSITE_TEST = "1 AND 2 AND (3 OR 4)"
    BOOL_OP = COMPOSITE
    TEST_CLAUSE:
      TEST @Value(STATUS) != 0
      TEST @Value(CircuitIds) CONTAINS @Value(CIRCUITID)
      TEST @Value(clientFeederType) = @Value(FEEDERTYPE)
      TEST @Value(clientFeederType) = -1
    PASSED -> SetElectricStitchPointBlockName_2
SetElectricStitchPointBlockName_2: AttributeCreator
    ATTR_LIST = autocad_block_name,"FME_CONDITIONAL:DEFAULT_VALUE'_FME_NO_OP_'BOOL_OP;OR;COMPOSITE_TEST;<Unused>;TEST @Value(SUBTYPECD) = 2'EESUB'BOOL_OP;OR;COMPOSITE_TEST;<Unused>;TEST @Value(SUBTYPECD) = 1'EESUB'FME_NUM_CONDITIONS3___",autocad_layer,MAP-ELEC-EXIST-DOH,output_file_name,$(output_file_name),autocad_entity,autocad_insert
    -> AttributeRenamer
AttributeRenamer
    ATTR_LIST = UOID,OBJECTID,"",UGUID,GLOBALID,""
    -> SetScale
SetScale
    scale = $(scale)
    SetScaleFromScaleFactor_Output -> RotateToCAD
    SetScaleFromScaleFactor_Output -> AttributeCreator_2
    SetScaleFromScaleFactor_Output -> FeatureMerger [input 2]
RotateToCAD
    SYMBOLROTATION = @Value(ROTATION)
    RotateToCADTemplate_Output -> Features (output)
Features (output)
AttributeCreator_2
    ATTR_LIST = _labelstring,"FME_CONDITIONAL:DEFAULT_VALUE''BOOL_OP;OR;COMPOSITE_TEST;<Unused>;TEST CIRCUITID NOT_ATTRIBUTE_IS_EMPTY _FME_BLANK_STRING_'@Right(@Value(CIRCUITID),4)'FME_NUM_CONDITIONS2___"
    -> LabelPointReplacer
LabelPointReplacer
    ALWAYSROTATE = yes
    LABATTR = @Value(_labelstring)
    HEIGHT = 4
    LabelPoint -> AnnotationToMText
AnnotationToMText
    XSCALE = .54
    fme_geometry = " "
    FONTNAME = RomanS
    YSCALE = .54
    BOLD = 0
    ITALIC = 0
    GEODB_TEXT_STRING = @Value(_labelstring)
    SCALE = $(scale)
    Tester_Passed -> AttributeCreator
AttributeCreator
    ATTR_LIST = autocad_justification,autocad_middle_middle,autocad_rotation,@Value(ROTATION),autocad_color,7
    -> Labels (output)
Labels (output)
AnnotationToMText_2_AttributeCreator_8_Input (input)
    -> RemoveUnplacedAnno
RemoveUnplacedAnno
    STATUS = @Value(STATUS)
    RemoveUnplaced_Passed -> AnnotationToMText_4
AnnotationToMText_4
    XSCALE = .54
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> FeatureMerger [input 1]
FeatureMerger
    PROCESS_DUPS = No
    MERGE_TYPE = Attributes Only
    SUPPLIERS_FIRST = No
    JOIN_KEYS = @Value(FEATUREID) @Value(OBJECTID) AUTO
    SUPPLIER_PREFIX_DUMMY = YES
    MERGED -> Anno (output)
Anno (output)

FME custom transformer ProcessDCRectifier_and_Anno

Parameters:
- output_file_name = schm_to_cad
- scale = 500
- SCHEMATICTID = @Value(SCHEMATICTID)   # Schematictid
- UOID = @Value(UOID)   # Uoid
- UGUID = @Value(UGUID)   # Uguid
- SUBTYPE = @Value(SUBTYPE)   # Subtype
- OPERATINGVOLTAGE = @Value(OPERATINGVOLTAGE)   # Operatingvoltage
- CLIENTOPERATINGVOLTAGE = @Value(clientOperatingVoltage)   # Clientoperatingvoltage
- STATUS = @Value(STATUS)   # Status
- CIRCUITID = @Value(CIRCUITID)   # Circuitid
- CIRCUITIDS = @Value(CircuitIds)   # Circuitids

SetElectricStitchPointBlockName_3_Input (input)
    -> Tester
Tester
    TEST_MODE = Automatic
    TEST_DESCRIPTION = ""
    BOOL_OP = OR
    TEST_CLAUSE = TEST @Value(SUBTYPE) = 1
    PASSED -> Tester_3
Tester_3
    TEST_MODE = Automatic
    TEST_DESCRIPTION = ""
    COMPOSITE_TEST = "1 AND 2 AND (3 OR 4)"
    BOOL_OP = COMPOSITE
    TEST_CLAUSE:
      TEST @Value(STATUS) != 0
      TEST @Value(CircuitIds) CONTAINS @Value(CIRCUITID)
      TEST @Value(clientOperatingVoltage) = @Value(OPERATINGVOLTAGE)
      TEST @Value(clientOperatingVoltage) = -1
    PASSED -> SetDCRectifierBlockName_3
SetDCRectifierBlockName_3: AttributeCreator
    ATTR_LIST = autocad_block_name,EEDCREC,autocad_layer,MAP-ELEC-EXIST-DUG,output_file_name,$(output_file_name),autocad_entity,autocad_insert
    -> AttributeRemover
AttributeRemover
    REMOVE_ATTRS = autocad_entity
    -> AttributeRenamer_3
AttributeRenamer_3
    ATTR_LIST = UOID,OBJECTID,"",UGUID,GLOBALID,""
    -> SetScale_21
SetScale_21
    scale = $(scale)
    SetScaleFromScaleFactor_Output -> Features (output)
Features (output)

FME custom transformer DonutRemover

Parameters:
- FME_GEOMETRY = @Value(fme_geometry)   # Fme Geometry

DonutTester_Input (input)
    -> DonutTester
DonutTester: Tester
    TEST_MODE = Automatic
    TEST_DESCRIPTION = ""
    BOOL_OP = OR
    TEST_CLAUSE = TEST @Value(fme_geometry) = fme_donut
    PASSED -> DonutHoleExtractor
    FAILED -> NotDonut (output)
DonutHoleExtractor
    OUTERSHELL -> DonutParts (output)
    HOLE -> DonutParts (output)
DonutParts (output)
NotDonut (output)

FME custom transformer ProcessOpenPoint

Parameters:
- output_file_name = schm_to_cad
- RATEDAMPS = @Value(RATEDAMPS)   # Ratedamps
- STATUS = @Value(STATUS)   # Status
- scale = 500
- SCHEMATICTID = @Value(SCHEMATICTID)   # Schematictid
- UOID = @Value(UOID)   # Uoid
- SUBTYPE = @Value(SUBTYPE)   # Subtype
- UGUID = @Value(UGUID)   # Uguid
- CIRCUITID = @Value(CIRCUITID)   # Circuitid
- CIRCUITIDS = @Value(CircuitIds)   # Circuitids
- OPERATINGVOLTAGE = @Value(OPERATINGVOLTAGE)   # Operatingvoltage
- FEEDERTYPE = @Value(FEEDERTYPE)   # Feedertype
- CLIENTFEEDERTYPE = @Value(clientFeederType)   # Clientfeedertype
- CLIENTOPERATINGVOLTAGE = @Value(clientOperatingVoltage)   # Clientoperatingvoltage

SetOpenPointBlockName_Input (input)
    -> SetOpenPointBlockName1
SetOpenPointBlockName1: AttributeCreator
    ATTR_LIST = autocad_block_name,"FME_CONDITIONAL:DEFAULT_VALUE'EEOPDEFAULT'BOOL_OP;OR;COMPOSITE_TEST;<Unused>;TEST @Value(SUBTYPE) = 1'EE200LB'BOOL_OP;AND;COMPOSITE_TEST;<Unused>;TEST @Value(SUBTYPE) = 2;TEST @Value(RATEDAMPS) != 600'EE200DB'BOOL_OP;AND;COMPOSITE_TEST;<Unused>;TEST @Value(SUBTYPE) = 2;TEST @Value(RATEDAMPS) = 600'EE600DB'BOOL_OP;AND;COMPOSITE_TEST;<Unused>;TEST @Value(SUBTYPE) = 3;TEST @Value(RATEDAMPS) = 0'EESECOP'BOOL_OP;AND;COMPOSITE_TEST;<Unused>;TEST @Value(SUBTYPE) = 4;TEST @Value(RATEDAMPS) = 0'EEPOP'BOOL_OP;AND;COMPOSITE_TEST;<Unused>;TEST @Value(SUBTYPE) = 9;TEST @Value(RATEDAMPS) = 0'EECC'BOOL_OP;AND;COMPOSITE_TEST;<Unused>;TEST @Value(SUBTYPE) = 5;TEST RATEDAMPS ATTRIBUTE_VALUE_NULL _FME_BLANK_STRING_'EESPLDB'BOOL_OP;AND;COMPOSITE_TEST;<Unused>;TEST @Value(SUBTYPE) = 6;TEST RATEDAMPS ATTRIBUTE_VALUE_NULL _FME_BLANK_STRING_'EEOPTERM'BOOL_OP;AND;COMPOSITE_TEST;<Unused>;TEST @Value(SUBTYPE) = 7;TEST @Value(RATEDAMPS) = 200'EE200OPTEE'BOOL_OP;AND;COMPOSITE_TEST;<Unused>;TEST @Value(SUBTYPE) = 7;TEST @Value(RATEDAMPS) = 600'EE600OPTEE'BOOL_OP;AND;COMPOSITE_TEST;<Unused>;TEST $(SUBTYPE) = 8;TEST RATEDAMPS ATTRIBUTE_VALUE_NULL _FME_BLANK_STRING_'EEOPSJ'BOOL_OP;AND;COMPOSITE_TEST;<Unused>;TEST @Value(SUBTYPE) = 10;TEST RATEDAMPS ATTRIBUTE_VALUE_NULL _FME_BLANK_STRING_'EELIMIT'BOOL_OP;OR;COMPOSITE_TEST;<Unused>;TEST @Value(SUBTYPE) = 12'EETEECON'BOOL_OP;AND;COMPOSITE_TEST;<Unused>;TEST @Value(STATUS) = 0'PEOPDEFAULT'FME_NUM_CONDITIONS15___",output_file_name,$(output_file_name),autocad_entity,autocad_insert
    -> Tester_3
Tester_3
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> AttributeRenamer
AttributeRenamer
    ATTR_LIST = UOID,OBJECTID,"",UGUID,GLOBALID,""
    -> SetLayerOHUGOpenPoint
SetLayerOHUGOpenPoint
    SUBTYPE = @Value(SUBTYPE)
    -> SetScale_21
SetScale_21
    scale = $(scale)
    SetScaleFromScaleFactor_Output -> Features (output)
Features (output)
RemovePseudoOpenPoints: Tester [off]
    TEST_MODE = Automatic
    TEST_DESCRIPTION = ""
    BOOL_OP = OR
    TEST_CLAUSE = TEST @Value(SUBTYPE) IN 3,9

FME custom transformer SetOHUGDPD

Parameters:
- SUBTYPE = @Value(SUBTYPE)   # Subtype

SetLayerOHUGFromInstallation1_3_SetLayerNameOHUG_Input (input)
    -> SetLayerNameOHUG_3
SetLayerNameOHUG_3: AttributeCreator
    ATTR_LIST = autocad_layer,"FME_CONDITIONAL:DEFAULT_VALUE'_FME_NO_OP_'BOOL_OP;AND;COMPOSITE_TEST;<Unused>;TEST @Value(SUBTYPE) IN 3,8'MAP-ELEC-EXIST-DOH'BOOL_OP;AND;COMPOSITE_TEST;<Unused>;TEST @Value(SUBTYPE) = 2'MAP-ELEC-EXIST-DUG'FME_NUM_CONDITIONS3___"
    -> SetLayerOHUGFromInstallation1_3_SetLayerNameOHUG_Output (output)
SetLayerOHUGFromInstallation1_3_SetLayerNameOHUG_Output (output)

FME custom transformer ProcessVoltageRegulator_and_Anno

Parameters:
- output_file_name = schm_to_cad
- SYMBOLNUMBER = @Value(SYMBOLNUMBER)   # Symbolnumber
- FONTNAME = @Value(FONTNAME)   # Fontname
- BOLD = @Value(BOLD)   # Bold
- OBJECTID = @Value(OBJECTID)   # Objectid
- GEODB_TEXT_STRING = @Value(geodb_text_string)   # Geodb Text String
- FME_GEOMETRY = @Value(fme_geometry)   # Fme Geometry
- FEATUREID = @Value(FEATUREID)   # Featureid
- ITALIC = @Value(ITALIC)   # Italic
- ANNOTATIONCLASSID = @Value(ANNOTATIONCLASSID)   # Annotationclassid
- STATUS = @Value(STATUS)   # Status
- scale = 500
- XOFFSET = @Value(XOFFSET)   # Xoffset
- UOID = @Value(UOID)   # Uoid
- SUBTYPE = @Value(SUBTYPE)   # Subtype
- UGUID = @Value(UGUID)   # Uguid
- CIRCUITID = @Value(CIRCUITID)   # Circuitid
- CIRCUITIDS = @Value(CircuitIds)   # Circuitids
- OPERATINGVOLTAGE = @Value(OPERATINGVOLTAGE)   # Operatingvoltage
- FEEDERTYPE = @Value(FEEDERTYPE)   # Feedertype
- CLIENTFEEDERTYPE = @Value(clientFeederType)   # Clientfeedertype
- CLIENTOPERATINGVOLTAGE = @Value(clientOperatingVoltage)   # Clientoperatingvoltage

SetVoltageRegulatorBlockName_Input (input)
    -> Tester_2
Tester_2
    TEST_MODE = Automatic
    TEST_DESCRIPTION = ""
    BOOL_OP = AND
    TEST_CLAUSE = TEST @Value(SUBTYPE) IN 1,2,3
    PASSED -> SetVoltageRegulatorBlockName1
SetVoltageRegulatorBlockName1: AttributeCreator
    ATTR_LIST = autocad_block_name,"FME_CONDITIONAL:DEFAULT_VALUE'EEVRDEFAULT'BOOL_OP;OR;COMPOSITE_TEST;<Unused>;TEST @Value(SYMBOLNUMBER) = 57'EEREGBIOH'BOOL_OP;OR;COMPOSITE_TEST;<Unused>;TEST @Value(SYMBOLNUMBER) = 58'EEREGLFOH'BOOL_OP;OR;COMPOSITE_TEST;<Unused>;TEST @Value(SYMBOLNUMBER) = 59'EEREGRTOH'BOOL_OP;OR;COMPOSITE_TEST;<Unused>;TEST @Value(SYMBOLNUMBER) = 60'EEREGBIPAD'BOOL_OP;OR;COMPOSITE_TEST;<Unused>;TEST @Value(SYMBOLNUMBER) = 61'EEREGLFPAD'BOOL_OP;OR;COMPOSITE_TEST;<Unused>;TEST @Value(SYMBOLNUMBER) = 62'EEREGRTPAD'BOOL_OP;OR;COMPOSITE_TEST;<Unused>;TEST @Value(SYMBOLNUMBER) = 63'EEBBNKLF'BOOL_OP;OR;COMPOSITE_TEST;<Unused>;TEST @Value(SYMBOLNUMBER) = 64'EEBBNKRT'BOOL_OP;OR;COMPOSITE_TEST;<Unused>;TEST @Value(SYMBOLNUMBER) = 65'EEBBNK2LF'BOOL_OP;OR;COMPOSITE_TEST;<Unused>;TEST @Value(SYMBOLNUMBER) = 66'EEBBNK2RT'BOOL_OP;OR;COMPOSITE_TEST;<Unused>;TEST @Value(SYMBOLNUMBER) = 67'EEAUTOBI'BOOL_OP;OR;COMPOSITE_TEST;<Unused>;TEST @Value(SYMBOLNUMBER) = 68'EEAUTO2BI'BOOL_OP;OR;COMPOSITE_TEST;<Unused>;TEST @Value(SYMBOLNUMBER) = 71'EEREGLFSUPOH'BOOL_OP;OR;COMPOSITE_TEST;<Unused>;TEST @Value(SYMBOLNUMBER) = 72'EEREGRTSUPOH'BOOL_OP;OR;COMPOSITE_TEST;<Unused>;TEST @Value(SYMBOLNUMBER) = 73'EEREGBISUPOH'BOOL_OP;OR;COMPOSITE_TEST;<Unused>;TEST @Value(SYMBOLNUMBER) = 56'EERG'BOOL_OP;OR;COMPOSITE_TEST;<Unused>;TEST @Value(SYMBOLNUMBER) = 74'EEBBNKBI'BOOL_OP;OR;COMPOSITE_TEST;<Unused>;TEST @Value(SYMBOLNUMBER) = 75'EEBBNK2BI'BOOL_OP;OR;COMPOSITE_TEST;<Unused>;TEST @Value(SYMBOLNUMBER) = 76'EEAUTO2LF'BOOL_OP;OR;COMPOSITE_TEST;<Unused>;TEST @Value(SYMBOLNUMBER) = 77'EEAUTO2RF'BOOL_OP;OR;COMPOSITE_TEST;<Unused>;TEST @Value(SYMBOLNUMBER) = 78'EEAUTOLF'BOOL_OP;OR;COMPOSITE_TEST;<Unused>;TEST @Value(SYMBOLNUMBER) = 79'EEAUTORF'BOOL_OP;OR;COMPOSITE_TEST;<Unused>;TEST @Value(SYMBOLNUMBER) = 80'EEBBNK3BI'BOOL_OP;OR;COMPOSITE_TEST;<Unused>;TEST @Value(STATUS) = 0'PEVRDEFAULT'FME_NUM_CONDITIONS25___",output_file_name,$(output_file_name),autocad_entity,autocad_insert
    -> Tester_4
Tester_4
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> AttributeRenamer
AttributeRenamer
    ATTR_LIST = UOID,OBJECTID,"",UGUID,GLOBALID,""
    -> SetLayerOHUGVolatageRegulator
SetLayerOHUGVolatageRegulator
    SUBTYPE = @Value(SUBTYPE)
    -> SetScale_21
SetScale_21
    scale = $(scale)
    SetScaleFromScaleFactor_Output -> Features (output)
    SetScaleFromScaleFactor_Output -> FeatureMerger_VR [input 2]
Features (output)
AnnotationToMText_SStruct1_AttributeCreator_8_Input (input)
    -> RemoveUnplacedAnno
RemoveUnplacedAnno
    STATUS = @Value(STATUS)
    RemoveUnplaced_Passed -> AnnotationToMText_VR
AnnotationToMText_VR
    XSCALE = .54
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> FeatureMerger_VR [input 1]
FeatureMerger_VR
    PROCESS_DUPS = No
    MERGE_TYPE = Attributes Only
    SUPPLIERS_FIRST = No
    JOIN_KEYS = @Value(FEATUREID) @Value(OBJECTID) AUTO
    SUPPLIER_PREFIX_DUMMY = YES
    MERGED -> Anno (output)
Anno (output)

FME custom transformer ProcessCapacitorBank_and_Anno

Parameters:
- FONTNAME = @Value(FONTNAME)   # Fontname
- BOLD = @Value(BOLD)   # Bold
- OBJECTID = @Value(OBJECTID)   # Objectid
- GEODB_TEXT_STRING = @Value(geodb_text_string)   # Geodb Text String
- FME_GEOMETRY = @Value(fme_geometry)   # Fme Geometry
- FEATUREID = @Value(FEATUREID)   # Featureid
- ITALIC = @Value(ITALIC)   # Italic
- INSTALLATIONTYPE_2 = @Value(INSTALLATIONTYPE)   # Installationtype
- SYMBOLNUMBER_2 = @Value(SYMBOLNUMBER)   # Symbolnumber
- ANNOTATIONCLASSID = @Value(ANNOTATIONCLASSID)   # Annotationclassid
- STATUS = @Value(STATUS)   # Status
- scale = 500
- SCHEMATICTID = @Value(SCHEMATICTID)   # Schematictid
- UOID = @Value(UOID)   # Uoid
- SUBTYPE = @Value(SUBTYPE)   # Subtype
- UGUID = @Value(UGUID)   # Uguid
- CIRCUITID = @Value(CIRCUITID)   # Circuitid
- CIRCUITIDS = @Value(CircuitIds)   # Circuitids
- FEEDERTYPE = @Value(FEEDERTYPE)   # Feedertype
- OPERATINGVOLTAGE = @Value(OPERATINGVOLTAGE)   # Operatingvoltage
- CLIENTFEEDERTYPE = @Value(clientFeederType)   # Clientfeedertype
- CLIENTOPERATINGVOLTAGE = @Value(clientOperatingVoltage)   # Clientoperatingvoltage

BlockNameCapacitorBank_Input (input)
    -> BlockNameCapacitorBank
BlockNameCapacitorBank: AttributeCreator
    ATTR_LIST = autocad_block_name,"FME_CONDITIONAL:DEFAULT_VALUE'EECAPDEFAULT'BOOL_OP;AND;COMPOSITE_TEST;<Unused>;TEST @Value(SYMBOLNUMBER) = 2;TEST @Value(INSTALLATIONTYPE) = OH;TEST @Value(STATUS) != 0'EECAPOH'BOOL_OP;AND;COMPOSITE_TEST;<Unused>;TEST @Value(SYMBOLNUMBER) = 2;TEST @Value(INSTALLATIONTYPE) != OH;TEST @Value(STATUS) != 0'EEPMCAP'BOOL_OP;AND;COMPOSITE_TEST;<Unused>;TEST @Value(SYMBOLNUMBER) = 101;TEST @Value(INSTALLATIONTYPE) = OH;TEST @Value(STATUS) != 0'EECAPSUPOH'BOOL_OP;AND;COMPOSITE_TEST;<Unused>;TEST @Value(SYMBOLNUMBER) = 101;TEST @Value(INSTALLATIONTYPE) != OH;TEST @Value(STATUS) != 0'EEMCAPSUPUG'BOOL_OP;AND;COMPOSITE_TEST;<Unused>;TEST @Value(SYMBOLNUMBER) = 3;TEST @Value(INSTALLATIONTYPE) = OH;TEST @Value(STATUS) != 0'EECAPOH'BOOL_OP;AND;COMPOSITE_TEST;<Unused>;TEST @Value(SYMBOLNUMBER) = 3;TEST @Value(INSTALLATIONTYPE) != OH;TEST @Value(STATUS) != 0'EEPMCAP'BOOL_OP;AND;COMPOSITE_TEST;<Unused>;TEST @Value(SYMBOLNUMBER) = 4;TEST @Value(INSTALLATIONTYPE) = OH;TEST @Value(STATUS) != 0'EECAPSUPOH'BOOL_OP;AND;COMPOSITE_TEST;<Unused>;TEST @Value(SYMBOLNUMBER) = 4;TEST @Value(INSTALLATIONTYPE) != OH;TEST @Value(STATUS) != 0'EEMCAPSUPUG'BOOL_OP;AND;COMPOSITE_TEST;<Unused>;TEST @Value(SYMBOLNUMBER) = 6;TEST @Value(INSTALLATIONTYPE) = OH;TEST @Value(STATUS) != 0'EESCAPOH'BOOL_OP;AND;COMPOSITE_TEST;<Unused>;TEST @Value(SYMBOLNUMBER) = 6;TEST @Value(INSTALLATIONTYPE) != OH;TEST @Value(STATUS) != 0'EESCAP'BOOL_OP;AND;COMPOSITE_TEST;<Unused>;TEST @Value(INSTALLATIONTYPE) = OH;TEST @Value(STATUS) = 0'PECAPOH'BOOL_OP;AND;COMPOSITE_TEST;<Unused>;TEST @Value(INSTALLATIONTYPE) != OH;TEST @Value(STATUS) = 0'PEPMCAP'BOOL_OP;AND;COMPOSITE_TEST;<Unused>;TEST @Value(STATUS) = 0'PECAPDEFAULT'FME_NUM_CONDITIONS14___"
    -> Tester_2
    -> Tester_3
Tester_2 [off]
    TEST_MODE = Automatic
    TEST_DESCRIPTION = ""
    BOOL_OP = AND
    TEST_CLAUSE:
      TEST @Value(STATUS) != 0
      TEST @Value(CircuitIds) CONTAINS @Value(CIRCUITID)
    PASSED -> AttributeRenamer
Tester_3
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> AttributeRenamer
AttributeRenamer
    ATTR_LIST = UOID,OBJECTID,"",UGUID,GLOBALID,""
    -> SetLayerOHUG
SetLayerOHUG
    STATUS = @Value(STATUS)
    INSTALLATIONTYPE = @Value(INSTALLATIONTYPE)
    -> SetScale_21
SetScale_21
    scale = $(scale)
    SetScaleFromScaleFactor_Output -> AttributeCreator
    SetScaleFromScaleFactor_Output -> AttributeRemover
AttributeCreator
    ATTR_LIST = autocad_color,ByLayer
    -> Features (output)
Features (output)
AttributeRemover
    REMOVE_ATTRS = INSTALLATIONTYPE
    -> FeatureMerger_2 [input 2]
AnnotationToMText_3_AttributeCreator_8_Input (input)
    -> RemoveUnplacedAnno
RemoveUnplacedAnno
    STATUS = @Value(STATUS)
    RemoveUnplaced_Passed -> AnnotationToMText_4
AnnotationToMText_4
    XSCALE = .54
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> FeatureMerger_2 [input 1]
FeatureMerger_2
    PROCESS_DUPS = No
    MERGE_TYPE = Attributes Only
    SUPPLIERS_FIRST = No
    JOIN_KEYS = @Value(FEATUREID) @Value(OBJECTID) AUTO
    SUPPLIER_PREFIX_DUMMY = YES
    MERGED -> Anno (output)
Anno (output)

FME custom transformer ProcessDPD

Parameters:
- output_file_name = schm_to_cad
- scale = 500
- SYMBOLNUMBER = @Value(SYMBOLNUMBER)   # Symbolnumber
- TEXTSTRING = @Value(TEXTSTRING)   # Textstring
- FONTNAME = @Value(FONTNAME)   # Fontname
- FONTSIZE = @Value(FONTSIZE)   # Fontsize
- BOLD = @Value(BOLD)   # Bold
- ITALIC = @Value(ITALIC)   # Italic
- FONTLEADING = @Value(FONTLEADING)   # Fontleading
- FME_GEOMETRY = @Value(fme_geometry)   # Fme Geometry
- GEODB_TEXT_STRING = @Value(geodb_text_string)   # Geodb Text String
- FEATUREID = @Value(FEATUREID)   # Featureid
- STATUS = @Value(STATUS)   # Status
- SCHEMATICTID = @Value(SCHEMATICTID)   # Schematictid
- UOID = @Value(UOID)   # Uoid
- ROTATION = @Value(ROTATION)   # Rotation
- UGUID = @Value(UGUID)   # Uguid
- CIRCUITID = @Value(CIRCUITID)   # Circuitid
- SUBTYPE = @Value(SUBTYPE)   # Subtype
- ANNOTATIONCLASSID = @Value(ANNOTATIONCLASSID)   # Annotationclassid
- CIRCUITIDS = @Value(CircuitIds)   # Circuitids
- OPERATINGVOLTAGE = @Value(OPERATINGVOLTAGE)   # Operatingvoltage
- FEEDERTYPE = @Value(FEEDERTYPE)   # Feedertype
- CLIENTOPERATINGVOLTAGE = @Value(clientOperatingVoltage)   # Clientoperatingvoltage
- CLIENTFEEDERTYPE = @Value(clientFeederType)   # Clientfeedertype

AnnoIn (input)
    -> RemoveUnplacedAnno
RemoveUnplacedAnno
    STATUS = @Value(STATUS)
    RemoveUnplaced_Passed -> AnnotationToMText_DG1
AnnotationToMText_DG1
    XSCALE = .54
    fme_geometry = @Value(fme_geometry)
    FONTNAME = @Value(FONTNAME)
    YSCALE = .54
    BOLD = @Value(BOLD)
    ITALIC = @Value(ITALIC)
    GEODB_TEXT_STRING = @Value(geodb_text_string)
    SCALE = $(scale)
    Tester_Passed -> FeatureMerger_DG1 [input 1]
SetDPDBlockName_Input (input)
    -> SetDPDBlockName1
SetDPDBlockName1: AttributeCreator
    ATTR_LIST = autocad_block_name,"FME_CONDITIONAL:DEFAULT_VALUE'EEDPDDEFAULT'BOOL_OP;COMPOSITE;COMPOSITE_TEST;(1 AND 2) OR (3 AND 4 AND 2);TEST @Value(SYMBOLNUMBER) = 9;TEST @Value(STATUS) != 0;TEST SYMBOLNUMBER ATTRIBUTE_VALUE_NULL _FME_BLANK_STRING_;TEST @Value(SUBTYPE) = 2'EESSINT'BOOL_OP;AND;COMPOSITE_TEST;<Unused>;TEST @Value(SYMBOLNUMBER) = 10;TEST @Value(STATUS) != 0'EESSINTSUP'BOOL_OP;COMPOSITE;COMPOSITE_TEST;((1 OR 2 OR 3) AND 4) OR (5 and 6 and 4);TEST @Value(SYMBOLNUMBER) = 11;TEST @Value(SYMBOLNUMBER) = 12;TEST @Value(SYMBOLNUMBER) = 98;TEST @Value(STATUS) != 0;TEST SYMBOLNUMBER ATTRIBUTE_VALUE_NULL _FME_BLANK_STRING_;TEST @Value(SUBTYPE) = 3'EERC'BOOL_OP;COMPOSITE;COMPOSITE_TEST;(1 OR 2 OR 3) AND 4;TEST @Value(SYMBOLNUMBER) = 13;TEST @Value(SYMBOLNUMBER) = 14;TEST @Value(SYMBOLNUMBER) = 102;TEST @Value(STATUS) != 0'EERCSUP'BOOL_OP;AND;COMPOSITE_TEST;<Unused>;TEST @Value(SYMBOLNUMBER) = 97;TEST @Value(STATUS) != 0'EERCCPX'BOOL_OP;AND;COMPOSITE_TEST;<Unused>;TEST @Value(SYMBOLNUMBER) = 103;TEST @Value(STATUS) != 0'EERCSUPFLS'BOOL_OP;COMPOSITE;COMPOSITE_TEST;(1 OR 2 OR 3 OR 4 or (6 AND 7)) AND 5;TEST @Value(SYMBOLNUMBER) = 104;TEST @Value(SYMBOLNUMBER) = 111;TEST @Value(SYMBOLNUMBER) = 120;TEST @Value(SYMBOLNUMBER) = 16;TEST @Value(STATUS) != 0;TEST SYMBOLNUMBER ATTRIBUTE_VALUE_NULL _FME_BLANK_STRING_;TEST @Value(SUBTYPE) = 8'EESEC'BOOL_OP;COMPOSITE;COMPOSITE_TEST;(1 OR 2 OR 3 ) AND 4;TEST @Value(SYMBOLNUMBER) = 105;TEST @Value(SYMBOLNUMBER) = 112;TEST @Value(SYMBOLNUMBER) = 121;TEST @Value(STATUS) != 0'EESECSUP'BOOL_OP;COMPOSITE;COMPOSITE_TEST;(1 OR 2 OR 3 ) AND 4;TEST @Value(SYMBOLNUMBER) = 113;TEST @Value(SYMBOLNUMBER) = 122;TEST @Value(SYMBOLNUMBER) = 106;TEST @Value(STATUS) != 0'EESECSUPFLSR'BOOL_OP;COMPOSITE;COMPOSITE_TEST;(1 OR 2 ) AND 3;TEST @Value(SYMBOLNUMBER) = 114;TEST @Value(SYMBOLNUMBER) = 123;TEST @Value(STATUS) != 0'EECSW'BOOL_OP;COMPOSITE;COMPOSITE_TEST;(1 OR 2 ) AND 3;TEST @Value(SYMBOLNUMBER) = 115;TEST @Value(SYMBOLNUMBER) = 124;TEST @Value(STATUS) != 0'EECSWSUP'BOOL_OP;COMPOSITE;COMPOSITE_TEST;(1 OR 2 OR 3 ) AND 4;TEST @Value(SYMBOLNUMBER) = 116;TEST @Value(SYMBOLNUMBER) = 125;TEST @Value(SYMBOLNUMBER) = 109;TEST @Value(STATUS) != 0'EESWSUPFLSR'BOOL_OP;COMPOSITE;COMPOSITE_TEST;(1 OR 2 ) AND 3;TEST @Value(SYMBOLNUMBER) = 117;TEST @Value(SYMBOLNUMBER) = 110;TEST @Value(STATUS) != 0'EERCSUPFLSR'BOOL_OP;AND;COMPOSITE_TEST;<Unused>;TEST @Value(SYMBOLNUMBER) = 118;TEST @Value(STATUS) != 0'EESECCPX'BOOL_OP;AND;COMPOSITE_TEST;<Unused>;TEST @Value(SYMBOLNUMBER) = 119;TEST @Value(STATUS) != 0'EESWCPX'BOOL_OP;AND;COMPOSITE_TEST;<Unused>;TEST @Value(SYMBOLNUMBER) = 32;TEST @Value(STATUS) != 0'EESCMSECSUP'BOOL_OP;AND;COMPOSITE_TEST;<Unused>;TEST @Value(SYMBOLNUMBER) = 107;TEST @Value(STATUS) != 0'EECSW'BOOL_OP;AND;COMPOSITE_TEST;<Unused>;TEST @Value(SYMBOLNUMBER) = 108;TEST @Value(STATUS) != 0'EECSWSUP'BOOL_OP;AND;COMPOSITE_TEST;<Unused>;TEST @Value(SUBTYPE) = 2;TEST @Value(STATUS) = 0'EESSINT'BOOL_OP;AND;COMPOSITE_TEST;<Unused>;TEST @Value(SUBTYPE) = 3;TEST @Value(STATUS) = 0'EERC'BOOL_OP;AND;COMPOSITE_TEST;<Unused>;TEST @Value(SUBTYPE) = 8;TEST @Value(STATUS) = 0'PESEC'BOOL_OP;AND;COMPOSITE_TEST;<Unused>;TEST @Value(STATUS) = 0'PEDPDDEFAULT'BOOL_OP;AND;COMPOSITE_TEST;<Unused>;TEST @Value(SYMBOLNUMBER) = 17;TEST @Value(STATUS) != 0;TEST @Value(SUBTYPE) = 3'EERCTS'BOOL_OP;AND;COMPOSITE_TEST;<Unused>;TEST @Value(SYMBOLNUMBER) = 18;TEST @Value(STATUS) != 0;TEST @Value(SUBTYPE) = 3'EERCFS'BOOL_OP;AND;COMPOSITE_TEST;<Unused>;TEST @Value(SYMBOLNUMBER) = 127;TEST @Value(STATUS) != 0;TEST @Value(SUBTYPE) = 3'EERCFSS'FME_NUM_CONDITIONS26___"
    -> Tester_2
Tester_2
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> AttributeRenamer
AttributeRenamer
    ATTR_LIST = UOID,OBJECTID,"",UGUID,GLOBALID,""
    -> SetOHUGDPD
SetOHUGDPD
    SUBTYPE = @Value(SUBTYPE)
    SetLayerOHUGFromInstallation1_3_SetLayerNameOHUG_Output -> AttributeCreator
AttributeCreator
    ATTR_LIST = output_file_name,$(output_file_name)
    -> AttributeCreator_2
AttributeCreator_2
    ATTR_LIST = autocad_entity,autocad_insert
    -> RotateToCAD_21
RotateToCAD_21
    SYMBOLROTATION = @Value(ROTATION)
    RotateToCADTemplate_Output -> SetScale_21
SetScale_21
    scale = $(scale)
    SetScaleFromScaleFactor_Output -> Features (output)
    SetScaleFromScaleFactor_Output -> FeatureMerger_DG1 [input 2]
FeatureMerger_DG1
    PROCESS_DUPS = No
    MERGE_TYPE = Attributes Only
    SUPPLIERS_FIRST = No
    JOIN_KEYS = @Value(FEATUREID) @Value(OBJECTID) AUTO
    SUPPLIER_PREFIX_DUMMY = YES
    MERGED -> Anno (output)
Anno (output)
Features (output)

FME custom transformer ProcessWaterP_and_Seg

Parameters:
- output_file_name = gis_to_cad1
- NAME = @Value(NAME)   # Name
- scale =   # Scale

Lines (input)
    -> Clipper [input 2]
Polygons (input)
    -> Clipper [input 2]
Polygon_to_Clipp (input)
    -> Clipper [input 1]
Clipper
    CREATE_AGGREGATES = Yes
    CLIPPED_ATTR = _clipped
    MERGE_ATTRS = No
    PRESERVE_CLIPPEE_EXTENTS = No
    ATTR_PREFIX = clipper_
    CLIP_TYPE = Multiple Clippers
    BOUNDARY_CASES = Treat as Inside
    INSIDE -> ProcessWaterP_and_Seg
ProcessWaterP_and_Seg: AttributeCreator
    ATTR_LIST = autocad_linetype,ELCANAL,autocad_layer,MAP-LAND-MISC,output_file_name,$(output_file_name)
    -> LabelPointReplacer
    -> Features (output)
LabelPointReplacer
    ALWAYSROTATE = yes
    LABATTR = @Value(NAME)
    HEIGHT = 8
    LabelPoint -> AnnotationToMTextNotes
AnnotationToMTextNotes
    XSCALE = .54
    fme_geometry = " "
    FONTNAME = RomanT
    YSCALE = .54
    BOLD = 0
    ITALIC = 0
    GEODB_TEXT_STRING = @Value(NAME)
    SCALE = $(scale)
    Tester_Passed -> AttributeCreator
AttributeCreator
    ATTR_LIST = autocad_color,ByBlock
    -> Labels (output)
Labels (output)
Features (output)

FME custom transformer SetLayerOHUGVolatageRegulator

Parameters:
- SUBTYPE = @Value(SUBTYPE)   # Subtype

Input (input)
    -> SetLayerNameOHUG_2
SetLayerNameOHUG_2: AttributeCreator
    ATTR_LIST = autocad_layer,"FME_CONDITIONAL:DEFAULT_VALUE'_FME_NO_OP_'BOOL_OP;AND;COMPOSITE_TEST;<Unused>;TEST @Value(SUBTYPE) IN 1,3'MAP-ELEC-EXIST-DOH'BOOL_OP;AND;COMPOSITE_TEST;<Unused>;TEST @Value(SUBTYPE) = 2'MAP-ELEC-EXIST-DUG'FME_NUM_CONDITIONS3___"
    -> Output (output)
Output (output)

FME custom transformer LabelToMText

Parameters:
- fme_geometry =   # Test Parameter
- XSCALE = .72   # X
- YSCALE = .72   # Y
- FONTNAME_2 = @Value(FontName)   # Fontname
- FONTSIZE = @Value(FontSize)   # Fontsize
- BOLD_2 = @Value(Bold)   # Bold
- ITALIC_2 = @Value(Italic)   # Italic
- TEXT = @Value(Text)   # Text

Input (input)
    -> Tester_1
Tester_1
    TEST_MODE = Automatic
    TEST_DESCRIPTION = ""
    BOOL_OP = OR
    TEST_CLAUSE = TEST $(fme_geometry) != fme_undefined
    PASSED -> AttributeCreator_1
Note: Create MText string, including / bold and italic settings
AttributeCreator_1
    ATTR_LIST = autocad_mtext_string,{\f@Value(FontName)|b@Value(Bold)|i@Value(Italic)|p34;@Value(Text)},autocad_entity,autocad_multi_text
    -> Scaler
Note: Scale text size to adjust to / ArcMap display size
Scaler
    XSCALE = $(XSCALE)
    SCALE_ORIGIN = Center Point
    YSCALE = $(YSCALE)
    TEXT_LOC_ONLY = Location and Size
    ZSCALE = 1
    RASTER_SCALING = Extents
    SCALED -> CharacterCodeExtractor
Note: Remove null characters / created when text was split
CharacterCodeExtractor
    SRC_ATTR = Text
    CODE_ATTR = _code
    -> Tester
Tester
    TEST_MODE = Automatic
    TEST_DESCRIPTION = ""
    BOOL_OP = AND
    TEST_CLAUSE:
      TEST @Value(Text) != ""
      TEST @Value(_code) < 129
    PASSED -> Tester_Passed (output)
Tester_Passed (output)

FME custom transformer ProcessBusBar

Parameters:
- STATUS = @Value(STATUS)   # Status
- SCHEMATICTID = @Value(SCHEMATICTID)   # Schematictid
- UOID = @Value(UOID)   # Uoid
- SUBTYPE = @Value(SUBTYPE)   # Subtype
- UGUID = @Value(UGUID)   # Uguid
- OUTPUT_FILE_NAME = schm_to_cad   # Output File Name
- SCHMCircuitID = 0
- CIRCUITID = @Value(CIRCUITID)   # Circuitid
- CIRCUITIDS = @Value(CircuitIds)   # Circuitids
- OPERATINGVOLTAGE = @Value(OPERATINGVOLTAGE)   # Operatingvoltage
- FEEDERTYPE = @Value(FEEDERTYPE)   # Feedertype
- CLIENTFEEDERTYPE = @Value(clientFeederType)   # Clientfeedertype
- CLIENTOPERATINGVOLTAGE = @Value(clientOperatingVoltage)   # Clientoperatingvoltage

ProcessBusBar_Input_1 (input)
    -> RemoveSecondaryBusBar
RemoveSecondaryBusBar: Tester
    TEST_MODE = Automatic
    TEST_DESCRIPTION = ""
    BOOL_OP = OR
    TEST_CLAUSE = TEST @Value(SUBTYPE) = 1
    PASSED -> Tester_3
Tester_3
    TEST_MODE = Automatic
    TEST_DESCRIPTION = ""
    COMPOSITE_TEST = "1 AND 2 AND ((3 AND 4) OR (3 AND 6) OR (4 AND 5) OR (5 AND 6))"
    BOOL_OP = COMPOSITE
    TEST_CLAUSE:
      TEST @Value(STATUS) != 0
      TEST @Value(CircuitIds) CONTAINS @Value(CIRCUITID)
      TEST @Value(clientFeederType) = @Value(FEEDERTYPE)
      TEST @Value(clientOperatingVoltage) = @Value(OPERATINGVOLTAGE)
      TEST @Value(clientFeederType) = -1
      TEST @Value(clientOperatingVoltage) = -1
    PASSED -> Tester_CircuitID_2
Tester_CircuitID_2
    TEST_MODE = Automatic
    TEST_DESCRIPTION = ""
    BOOL_OP = OR
    TEST_CLAUSE = TEST $(SCHMCircuitID) = 0
    PASSED -> ProcessBusBar
    FAILED -> Tester_CircuitID
Tester_CircuitID
    TEST_MODE = Automatic
    TEST_DESCRIPTION = ""
    COMPOSITE_TEST = 1
    BOOL_OP = COMPOSITE
    TEST_CLAUSE = TEST @Value(CIRCUITID) = $(SCHMCircuitID)
    PASSED -> ProcessBusBar
ProcessBusBar: AttributeCreator
    ATTR_LIST = autocad_linetype,EEBUS,autocad_layer,MAP-ELEC-EXIST-DUG,autocad_entity,autocad_line,autocad_color,3
    -> AttributeRenamer
AttributeRenamer
    ATTR_LIST = UOID,OBJECTID,"",UGUID,GLOBALID,""
    -> ProcessBusBar_Output_1 (output)
ProcessBusBar_Output_1 (output)
